[DOCUMENT]
TITLE: GBSK HVPS Interface Bootloader FW Verification Testing Protocol
UID: DHF-GBSK-0110
METADATA:
  COMPONENT: hvps-interface/bootloader

[GRAMMAR]
IMPORT_FROM_FILE: @grammar

[[SECTION]]
TITLE: Purpose

[TEXT]
STATEMENT: >>>
This document provides the full test protocol (a full collection of test cases) for the HVPS Interface
Bootloader Firmware for the GBSK 1.0 system.
<<<

[[/SECTION]]

[[SECTION]]
TITLE: Scope

[TEXT]
STATEMENT: >>>
This report contains a detailed test description to conduct verification testing of GBSK 1.0 HVPS
Interface Bootloader Firmware that covers GBSK HVPS Interface Bootloader FW SRS.
<<<

[[/SECTION]]

[[SECTION]]
TITLE: Abbreviations and Definitions

[TEXT]
STATEMENT: >>>
EC256
  Elliptic Curve Digital Signature Algorithm with 256-bit keys

FIH
  Fault Injection Hardening

FW
  Firmware

HVPS
  High Voltage Power Supply

RAM
  Random Access Memory

SDP
  Software Development Plan

SVP
  Software Verification Plan

SW
  Software

UART
  Universal Asynchronous Receiver Transmitter
<<<

[[/SECTION]]

[[SECTION]]
TITLE: References

[TEXT]
STATEMENT: >>>
DHF-GBSK-0001, Rev. 1: GBSK SDP

DHF-GBSK-0003, Rev. 1: GBSK SVP

[LINK: DHF-GBSK-0021]

DHF-GBSK-0031, Rev. 1: GBSK Firmware Architecture Description
<<<

[[/SECTION]]

[[SECTION]]
TITLE: Prerequisites

[TEXT]
STATEMENT: >>>
**Pre-Execution Approval**

A pre-execution meeting shall be held, and test execution shall be approved by the project
manager and QA/RA.

**Objective(s)**

Verify that:

* Software, firmware, hardware, and test equipment versions and configurations are recorded in
  the test report before execution.
* Test personnel are assigned and available.

**Assumptions & Constraints**

The following common prerequisites apply to all test cases, together with the prerequisites
listed in each case:

* The bootloader under test is programmed on the target board.
* The PC is connected to the board's UART3 interface. Serial communication uses 38400 baud,
  no parity, 8 data bits, and 1 stop bit unless a test case states otherwise.
* For cases using mcumgr, the command-line utility is installed and the PowerShell connection
  below is configured with an MTU of 128.
* Required image files are available at the paths used in the commands. A valid signed image
  is signed with a key trusted by the bootloader under test.
* Tools are available to record the command output, UART3 diagnostics, and application startup
  evidence required by each case. Only one tool has the serial port open at a time.

The examples use COM3; replace it with the serial port assigned to the test system in every
command that names the port.

Before executing mcumgr commands, define the connection in the PowerShell session used for
the test:

.. code-block:: powershell

   $conn = "dev=COM3,baud=38400,mtu=128"

J-Link and Ozone are required for the debugger-assisted case. PowerShell serial-port commands
are used where a case requires direct serial input.

**Acceptance Criteria**

Test execution can start when approval is recorded and all common and case-specific
prerequisites are met.
<<<

[[/SECTION]]

[[SECTION]]
PREFIX: TC-H1FWHVPSIB-
TITLE: Test Protocol

[TEST_CASE]
UID: TC-H1FWHVPSIB-5
TITLE: Authenticated Boot and Serial Recovery - Test Case
STATEMENT: >>>
Verify authenticated application boot, normal application startup, MCUboot serial communication,
and recovery after an invalid image is rejected.
<<<
PREREQUISITES: >>>
* The same known application is available in four forms: valid-signed.bin (valid signature),
  unsigned.bin (no signature), wrong-key.bin (signed with an untrusted key), and
  corrupt-header.bin (invalid MCUboot header).
* Normal startup of the known application can be identified and recorded.
<<<
STEPS: >>>
1. Place the board in serial recovery mode and read the image list. Replace COM3 with
   the board's serial port and ensure $conn uses the same port:

   .. code-block:: powershell

      $port = New-Object System.IO.Ports.SerialPort COM3,38400,None,8,one
      $port.Open()
      $port.Write("*B00TL`n")
      $port.Close()
      mcumgr --conntype serial --connstring $conn echo "recovery-check"

2. Record the image list before uploading:

   .. code-block:: powershell

      mcumgr --conntype serial --connstring $conn image list

3. Upload the correctly signed image:

   .. code-block:: powershell

      mcumgr --conntype serial --connstring $conn image upload valid-signed.bin

4. Record the image list after uploading, before resetting the board:

   .. code-block:: powershell

      mcumgr --conntype serial --connstring $conn image list

5. Reset the board:

   .. code-block:: powershell

      mcumgr --conntype serial --connstring $conn reset

6. After each reset, run:

   .. code-block:: powershell

      mcumgr --conntype serial --connstring $conn echo "recovery-check"

7. Repeat steps 2 through 6 separately for unsigned.bin, wrong-key.bin, and corrupt-header.bin,
   replacing valid-signed.bin in the upload command. Save the image-list output before and after
   each upload, including an empty list if the image is not reported.
<<<
EXPECTED_BEHAVIOR: >>>
1. The echo succeeds and displays "recovery-check" during the recovery interval.
2. The image-list request succeeds and its result is recorded before uploading.
3. mcumgr completes the valid-image upload.
4. The image-list request succeeds and reports the uploaded valid image's version and hash. 
5. The reset command succeeds. The valid application starts normally.
6. After valid-image upload and reset, the echo does not succeed and display "recovery-check".
   After each invalid-image upload and reset, the echo succeeds and displays "recovery-check".
7. Before/after image-list results are recorded for each invalid-image upload. 
   After each invalid-image upload, the imgage-list will show an empty list. After reset, 
   the bootloader rejects each invalid image, and none of them starts.
<<<
RELATIONS:
- TYPE: Parent
  VALUE: RQ-H1FWHVPSIB-1
  ROLE: Verifies
- TYPE: Parent
  VALUE: RQ-H1FWHVPSIB-4
  ROLE: Verifies
- TYPE: Parent
  VALUE: RQ-H1FWHVPSIB-5
  ROLE: Verifies
- TYPE: Parent
  VALUE: RQ-H1FWHVPSIB-9
  ROLE: Verifies
- TYPE: Parent
  VALUE: RQ-H1FWHVPSIB-10
  ROLE: Verifies

[TEST_CASE]
UID: TC-H1FWHVPSIB-6
TITLE: Oversized Image Upload Rejection - Test Case
STATEMENT: >>>
Verify that the bootloader rejects an application image larger than the 180 KiB primary slot.
<<<
PREREQUISITES: >>>
* The board is in serial recovery mode.
* An MCUboot image larger than the 180 KiB primary slot is available as oversized.bin.
<<<
STEPS: >>>
1. Read and save the image list before the upload attempt:

   .. code-block:: powershell

      mcumgr --conntype serial --connstring $conn image list

2. Use mcumgr to upload the oversized image to image 0 and observe the result:

   .. code-block:: powershell

      mcumgr --conntype serial --connstring $conn image upload oversized.bin

3. Read the image list again and compare it with the saved result:

   .. code-block:: powershell

      mcumgr --conntype serial --connstring $conn image list
<<<
EXPECTED_BEHAVIOR: >>>
1. The image-list request succeeds and its result is recorded.
2. The bootloader rejects the oversized image before programming it; the upload does not complete.
3. The image-list request still succeeds. The reported image entries, including any versions and
   hashes, match the result recorded before the upload attempt.
<<<
RELATIONS:
- TYPE: Parent
  VALUE: RQ-H1FWHVPSIB-2
  ROLE: Verifies
- TYPE: Parent
  VALUE: RQ-H1FWHVPSIB-11
  ROLE: Verifies

[TEST_CASE]
UID: TC-H1FWHVPSIB-7
TITLE: Progressive Application-Slot Erase - Test Case
STATEMENT: >>>
Verify that the bootloader erases and reprograms the required application flash pages when replacing
one valid application image with another.
<<<
PREREQUISITES: >>>
* Two different valid signed application images are available as image-A.bin and image-B.bin.
* The MCUboot image headers contain distinct, known versions A and B, respectively.
* Normal startup of applications A and B can be identified and recorded.
<<<
STEPS: >>>
1. Place the board in serial recovery mode and read the image list. Replace COM3 with
   the board's serial port and ensure $conn uses the same port:

   .. code-block:: powershell

      $port = New-Object System.IO.Ports.SerialPort COM3,38400,None,8,one
      $port.Open()
      $port.Write("*B00TL`n")
      $port.Close()
      mcumgr --conntype serial --connstring $conn image list

2. Upload image A:

   .. code-block:: powershell

      mcumgr --conntype serial --connstring $conn image upload image-A.bin

3. While still in serial recovery mode, read and record image A's version:

   .. code-block:: powershell

      mcumgr --conntype serial --connstring $conn image list

4. Reset the board:

   .. code-block:: powershell

      mcumgr --conntype serial --connstring $conn reset

5. Confirm that application A starts normally.
6. Place the board in serial recovery mode again.

7. Upload image B:

   .. code-block:: powershell

      mcumgr --conntype serial --connstring $conn image upload image-B.bin

8. While still in serial recovery mode, read and record image B's version:

   .. code-block:: powershell

      mcumgr --conntype serial --connstring $conn image list

9. Reset the board:

   .. code-block:: powershell

      mcumgr --conntype serial --connstring $conn reset

10. Confirm that application B starts normally.
<<<
EXPECTED_BEHAVIOR: >>>
1. The board enters serial recovery mode and responds to mcumgr.
2. The image-A.bin upload reaches 100 percent.
3. The image list reports version A in the primary slot.
4. The reset command succeeds.
5. The bootloader validates image A, and application A starts normally.
6. The board re-enters serial recovery mode, and the image list reports version A in the primary slot.
7. The image-B.bin upload reaches 100 percent. Completing this upload
   requires the bootloader to erase and reprogram the affected primary-slot flash pages.
8. The image list reports version B in the primary slot, replacing version A.
9. The reset command succeeds.
10. The bootloader validates image B, and application B starts normally.
<<<
RELATIONS:
- TYPE: Parent
  VALUE: RQ-H1FWHVPSIB-2
  ROLE: Verifies
- TYPE: Parent
  VALUE: RQ-H1FWHVPSIB-3
  ROLE: Verifies

[TEST_CASE]
UID: TC-H1FWHVPSIB-10
TITLE: Vector Table Validation - Test Case
STATEMENT: >>>
Verify that the bootloader accepts valid stack-pointer (SP) and reset-handler (RH) values and
rejects out-of-range values before application handoff.
<<<
PREREQUISITES: >>>
* A known valid signed application is installed on the target board.
* J-Link is connected to the board over SWD, and Ozone is configured for the target MCU.
* Ozone has loaded the ELF, debug symbols, and source matching the programmed bootloader.
<<<
STEPS: >>>
1. In Ozone, open jump_to_image() in Src/main.c. Using Disassembly, set hardware breakpoints
   after each vector value is loaded but before its range check, and at __disable_irq()
   before that instruction executes. The last breakpoint is the acceptance point.

2. Reset and run the bootloader without changing any values. Confirm BOOT_GO_OK on UART3 and
   that both checks pass to the acceptance point.

3. Reset for each run below. At the relevant breakpoint, edit only stack_ptr_val or
   image_reset_handler in Ozone's variable window, keeping the other value valid:

   * SP-MIN: stack_ptr_val = 0x20000000; expect acceptance.
   * SP-MAX: stack_ptr_val = 0x20008000; expect acceptance.
   * SP-BELOW: stack_ptr_val = 0x1FFFFFFC; expect ERR_SP and return without handoff.
   * SP-ABOVE: stack_ptr_val = 0x20008004; expect ERR_SP and return without handoff.
   * RH-BELOW: image_reset_handler = 0x08000001; expect ERR_RH and return without handoff.
   * RH-ABOVE: image_reset_handler = 0x08024001; expect ERR_RH and return without handoff.

   Change the loaded value, not flash or the active MSP. For optimized code, use Disassembly
   to identify its register or RAM location; inject before range-check arithmetic and confirm
   the value is not overwritten before comparison. If this cannot be confirmed, record the
   run as not executed.

4. Step through the check and record the injected value, result, and UART output. For accepted
   values, stop at the acceptance point and reset without continuing into the application.
   SP-MIN tests range acceptance only; it does not provide usable stack space below that address.
   For rejected values, stop when jump_to_image() returns to its caller, before another boot
   attempt reloads the valid values. Confirm no handoff or application VTOR/MSP setup occurred.

5. Remove the breakpoints, reset without injection, and confirm normal application startup.
<<<
EXPECTED_BEHAVIOR: >>>
1. The unchanged baseline passes both checks.

2. Both SP boundary values reach the acceptance point.

3. The two invalid SP values produce ERR_SP; the two invalid RH values produce ERR_RH.

  Each rejected run returns without application handoff.

4. Evidence is recorded for the baseline and all six injected runs, with results matching step 3.

5. The valid application starts normally after the final reset.

<<<
RELATIONS:
- TYPE: Parent
  VALUE: RQ-H1FWHVPSIB-6
  ROLE: Verifies
- TYPE: Parent
  VALUE: RQ-H1FWHVPSIB-7
  ROLE: Verifies

[TEST_CASE]
UID: TC-H1FWHVPSIB-15
TITLE: Invalid Serial Input - Test Case
STATEMENT: >>>
Verify that the bootloader ignores serial data that is not a valid MCUboot management packet and
remains available for serial recovery.
<<<
PREREQUISITES: >>>
* The board is configured to remain in serial recovery mode throughout the test, for example
  by having no valid application installed.
<<<
STEPS: >>>
1. Set the serial port (replace COM3 as needed), confirm communication, and record the image list.
   Run all steps in the same PowerShell session:

   .. code-block:: powershell

      $conn = "dev=COM3,baud=38400,mtu=128"
      mcumgr --conntype serial --connstring $conn echo "before-invalid-input"
      mcumgr --conntype serial --connstring $conn image list

2. Send a plain-text line that is not a valid MCUboot NLIP frame, then close the port:

   .. code-block:: powershell

      $port = [System.IO.Ports.SerialPort]::new("COM3", 38400)
      try {
          $port.Open()
          $port.Write("INVALID SERIAL DATA`n")
      } finally {
          $port.Close()
          $port.Dispose()
      }

3. Without resetting the board, confirm that serial recovery still responds:

   .. code-block:: powershell

      mcumgr --conntype serial --connstring $conn echo "recovery-check"

4. Read the image list again and compare it with step 1:

   .. code-block:: powershell

      mcumgr --conntype serial --connstring $conn image list
<<<
EXPECTED_BEHAVIOR: >>>
1. The echo displays "before-invalid-input", and the image-list request succeeds. Record its
   result, including an empty list if no image is reported.
2. The invalid line is ignored; it does not start an application, change the installed image, or
   cause the bootloader to reset or stop responding.
3. The mcumgr echo succeeds and displays "recovery-check" without a manual reset.
4. The image-list request succeeds, and the reported entries, versions, and hashes match step 1.
<<<
RELATIONS:
- TYPE: Parent
  VALUE: RQ-H1FWHVPSIB-11
  ROLE: Verifies

[TEST_CASE]
UID: TC-H1FWHVPSIB-16
TITLE: Interrupted Upload Recovery - Test Case
STATEMENT: >>>
Verify that interruption of a single-slot upload leaves the device in serial recovery and permits a
subsequent valid upload.
<<<
PREREQUISITES: >>>
* A valid signed application image is available as valid-image.bin.
* The expected version and hash of valid-image.bin are recorded for comparison with the image list.
* Normal startup of the application can be identified and recorded.
<<<
STEPS: >>>
1. Place the board in serial recovery mode and record the image list before uploading:

   .. code-block:: powershell

      mcumgr --conntype serial --connstring $conn image list

2. Begin the upload with mcumgr:

   .. code-block:: powershell

      mcumgr --conntype serial --connstring $conn image upload valid-image.bin

3. While upload progress is between 1 and 99 percent, press Ctrl+C to stop mcumgr.
4. Record the image list after the interrupted upload:

   .. code-block:: powershell

      mcumgr --conntype serial --connstring $conn image list

5. Reset or power-cycle the board.
6. Verify recovery availability:

   .. code-block:: powershell

      mcumgr --conntype serial --connstring $conn echo "recovery-check"

7. Run the upload command again and allow it to reach 100 percent:

   .. code-block:: powershell

      mcumgr --conntype serial --connstring $conn image upload valid-image.bin

8. Record the image list after the completed upload, before resetting:

   .. code-block:: powershell

      mcumgr --conntype serial --connstring $conn image list

9. Reset the board:

   .. code-block:: powershell

      mcumgr --conntype serial --connstring $conn reset

10. Observe application startup.
<<<
EXPECTED_BEHAVIOR: >>>
1. The image-list request succeeds and its result is recorded.
2. mcumgr begins the upload and displays progress.
3. Ctrl+C stops the upload before completion.
4. The image-list request succeeds and its result is recorded, including an empty list if no
   image is reported. A listed entry alone does not prove the incomplete image is bootable.
5. The bootloader does not execute the incomplete application after reset.
6. The mcumgr echo succeeds in recovery mode.
7. The subsequent mcumgr upload reaches 100 percent.
8. The image list reports the completed image's version and hash.
9. The reset command succeeds.
10. BOOT_GO_OK is reported and the application starts.
<<<
RELATIONS:
- TYPE: Parent
  VALUE: RQ-H1FWHVPSIB-12
  ROLE: Verifies

[[/SECTION]]

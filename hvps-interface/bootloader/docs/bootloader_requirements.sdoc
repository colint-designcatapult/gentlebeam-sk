[DOCUMENT]
TITLE: GBSK HVPS Interface Bootloader FW Software Requirements Specification
UID: DHF-GBSK-0021
METADATA:
  COMPONENT: hvps-interface/bootloader

[GRAMMAR]
IMPORT_FROM_FILE: @grammar

[[SECTION]]
TITLE: Purpose

[TEXT]
STATEMENT: >>>
The purpose of this document is to provide Software Requirements Specifications for the GBSK HVPS
Interface Bootloader Firmware (FW).
<<<

[[/SECTION]]

[[SECTION]]
TITLE: Scope

[TEXT]
STATEMENT: >>>
This document describes all requirements of the GBSK HVPS Interface Bootloader FW.
The information in this document has been derived from the VoxelRay GBSK Product Requirements
Specification, as referenced in this document.

\*The term Software applies to both Software and Firmware systems.
<<<

[[/SECTION]]

[[SECTION]]
TITLE: Abbreviations and Definitions

[TEXT]
STATEMENT: >>>
CRC
  Cyclic Redundancy Check

EC256
  Elliptic Curve Digital Signature Algorithm with 256-bit keys

FIH
  Fault Injection Hardening

FW
  Firmware

HVPS
  High Voltage Power Supply

LED
  Light Emitting Diode

MCU
  Microcontroller Unit

PID
  Proportional Integral Derivative controller

PRS
  Product Requirements Specification

RAM
  Random Access Memory

SDP
  Software Development Plan

SRS
  Software Requirements Specification

SW
  Software
<<<

[[/SECTION]]

[[SECTION]]
TITLE: Overview

[TEXT]
STATEMENT: >>>
The HVPS Interface Bootloader firmware allows the system to be able to update the HVPS Interface
application firmware. The HVPS Interface Bootloader firmware runs on the MCU of the HVPS interface
board.
<<<

[[/SECTION]]

[[SECTION]]
TITLE: References

[TEXT]
STATEMENT: >>>
DHF-GBSK-0001, Rev. 1: GBSK Software Development Plan (SDP)

DHF-GBSK-0002: VoxelRay Product Requirements Specification (PRS)
<<<

[[/SECTION]]

[[SECTION]]
PREFIX: RQ-H1FWHVPSIB-
TITLE: Requirements

[REQUIREMENT]
UID: RQ-H1FWHVPSIB-1
TYPE: Functional
TITLE: Authenticated Application Boot
STATEMENT: >>>
The HVPS interface bootloader firmware shall transfer execution to the HVPS interface application
only after MCUboot validates the image header, SHA-256 integrity metadata, and EC256 signature using
the trusted public key compiled into the bootloader.
<<<

[REQUIREMENT]
UID: RQ-H1FWHVPSIB-2
TYPE: Functional
TITLE: Application Image Programming
STATEMENT: >>>
The HVPS interface bootloader firmware shall accept an MCUboot image-management upload for image 0
and program the received image data within the configured primary application slot without writing
outside that slot.
<<<

[REQUIREMENT]
UID: RQ-H1FWHVPSIB-3
TYPE: Functional
TITLE: Application Slot Erasure
STATEMENT: >>>
The HVPS interface bootloader firmware shall erase the 2048-byte physical flash pages required for
an application image upload and shall not erase flash outside the configured primary application
slot.
<<<

[REQUIREMENT]
UID: RQ-H1FWHVPSIB-4
TYPE: Functional
TITLE: PC Communication
STATEMENT: >>>
The HVPS interface bootloader firmware shall communicate with a PC over UART3 using the MCUboot
serial-management protocol with NLIP framing and shall respond to a management echo request to
indicate that the system is in bootloader mode.
<<<

[REQUIREMENT]
UID: RQ-H1FWHVPSIB-5
TYPE: Functional
TITLE: MCUboot Image Validation
STATEMENT: >>>
The HVPS interface bootloader firmware shall reject an image when its MCUboot header, SHA-256
integrity metadata, or EC256 signature is missing, malformed, or invalid, and shall remain available
for serial recovery rather than executing the rejected image.
<<<

[REQUIREMENT]
UID: RQ-H1FWHVPSIB-6
TYPE: Functional
TITLE: Stack Pointer Validation
STATEMENT: >>>
The HVPS interface bootloader firmware shall validate that the stack pointer value read from the
application image vector table resides within the inclusive RAM address range 0x20000000 through
0x20008000 before jumping to the application.
<<<

[REQUIREMENT]
UID: RQ-H1FWHVPSIB-7
TYPE: Functional
TITLE: Reset Handler Validation
STATEMENT: >>>
The HVPS interface bootloader firmware shall validate that the reset handler address read from the
application image vector table is greater than or equal to the application image start address and
less than the configured executable-image upper bound before jumping to the application.
<<<

[REQUIREMENT]
UID: RQ-H1FWHVPSIB-9
TYPE: Functional
TITLE: Serial Recovery
STATEMENT: >>>
The HVPS interface bootloader firmware shall provide a serial recovery interval before each boot
attempt and shall continue to provide serial recovery while no valid application image is available.
<<<

[REQUIREMENT]
UID: RQ-H1FWHVPSIB-10
TYPE: Functional
TITLE: Application Handoff
STATEMENT: >>>
The HVPS interface bootloader firmware shall transfer control to a validated application in a state
that permits normal application startup.
<<<

[REQUIREMENT]
UID: RQ-H1FWHVPSIB-11
TYPE: Functional
TITLE: Invalid Serial Input
STATEMENT: >>>
The HVPS interface bootloader firmware shall reject serial-management packets with invalid framing,
CRC, encoding, command data, upload offsets, or image bounds without executing unvalidated image
content or writing outside the primary application slot.
<<<

[REQUIREMENT]
UID: RQ-H1FWHVPSIB-12
TYPE: Functional
TITLE: Interrupted Update Recovery
STATEMENT: >>>
Following an interrupted or incomplete application upload, the HVPS interface bootloader firmware
shall reject the incomplete application image and remain available for a subsequent serial recovery
upload.
<<<

[[/SECTION]]

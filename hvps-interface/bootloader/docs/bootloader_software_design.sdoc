[DOCUMENT]
TITLE: GBSK HVPS Interface Bootloader FW Software Design Document
UID: DHF-GBSK-0105
METADATA:
  COMPONENT: hvps-interface/bootloader

[GRAMMAR]
IMPORT_FROM_FILE: @grammar

[[SECTION]]
TITLE: Purpose

[TEXT]
STATEMENT: >>>
The purpose of this document is to outline the design specifications of the GBSK HVPS Interface
Bootloader Firmware.
<<<

[[/SECTION]]

[[SECTION]]
TITLE: Scope

[TEXT]
STATEMENT: >>>
This document describes the design modules and sub-modules of the GBSK HVPS Interface
Bootloader Firmware.
The information in this document is derived from the HVPS Interface Bootloader FW SRS, referenced in
this document.

\*The term Software applies to both Software and Firmware components.
<<<

[[/SECTION]]

[[SECTION]]
TITLE: Abbreviations and Definitions

[TEXT]
STATEMENT: >>>
EC256
  Elliptic Curve Digital Signature Algorithm with 256-bit keys

FIH
  Fault Injection Hardening

FW
  Firmware

MCU
  Microcontroller Unit

PRS
  Product Requirements Specification

RAM
  Random Access Memory

SDP
  Software Development Plan

SRS
  Software Requirements Specification

SW
  Software

UART
  Universal Asynchronous Receiver Transmitter

VTOR
  Vector Table Offset Register
<<<

[[/SECTION]]

[[SECTION]]
TITLE: Overview

[TEXT]
STATEMENT: >>>
The HVPS Interface Bootloader firmware allows the system to be able to update the HVPS Interface
application firmware. The HVPS Interface Bootloader firmware runs on the MCU of the HVPS interface
board.
<<<

[[/SECTION]]

[[SECTION]]
TITLE: References

[TEXT]
STATEMENT: >>>
DHF-GBSK-0001, Rev. 1: GBSK Software Development Plan (SDP)

DHF-GBSK-0003, Rev. 1: GBSK Software Verification Plan (SVP)

DHF-GBSK-0021, Rev. 1: GBSK HVPS Interface Bootloader Software Requirements Specification (SRS)

DHF-GBSK-0031, Rev. 1: GBSK Firmware Architecture Description
<<<

[[/SECTION]]

[[SECTION]]
TITLE: Architecture Overview

[[SECTION]]
TITLE: High Level System Architecture

[TEXT]
STATEMENT: >>>
See source document DHF-GBSK-0105 for the high-level system architecture diagram.
<<<

[[/SECTION]]

[[SECTION]]
TITLE: Main Modules

[TEXT]
STATEMENT: >>>
HVPS Bootloader Firmware - The firmware occupies the first 48 KiB of MCU flash. It validates a
signed MCUboot image in a single 180 KiB primary slot and either transfers execution to the
application or remains available for serial recovery.

Firmware Packaging Tools - The image creation utility converts an application Intel HEX artifact
into an MCUboot image with a 512-byte header and signs it using ECDSA P-256. The upload utility or
the standard mcumgr client transfers the packaged image to image 0 over UART3.

Flash Memory - The MCU flash contains a bootloader region beginning at 0x08000000 and a primary
application slot beginning at 0x0800C000. The application vector table normally begins at
0x0800C200 after the MCUboot header.
<<<

[[/SECTION]]

[[SECTION]]
PREFIX: SW-H1FWHVPSIB-
TITLE: Design Items

[DESIGN_ITEM]
UID: SW-H1FWHVPSIB-11
TITLE: Application Validation and Boot Selection
STATEMENT: >>>
After peripheral initialization, the bootloader opens a three-second MCUboot serial-recovery window
and then invokes boot_go(). MCUboot validates the primary-slot image header, SHA-256 TLV, and EC256
signature against the public key compiled into the bootloader. On success the firmware reports
BOOT_GO_OK and performs the protected application handoff. On failure it reports BOOT_GO_FAIL once
and repeats the serial-recovery and validation loop without executing the image.
<<<
RELATIONS:
- TYPE: Parent
  VALUE: RQ-H1FWHVPSIB-1
  ROLE: Refines
- TYPE: Parent
  VALUE: RQ-H1FWHVPSIB-5
  ROLE: Refines
- TYPE: Parent
  VALUE: RQ-H1FWHVPSIB-9
  ROLE: Refines
- TYPE: Parent
  VALUE: RQ-H1FWHVPSIB-12
  ROLE: Refines

[DESIGN_ITEM]
UID: SW-H1FWHVPSIB-13
TITLE: Primary-Slot Flash Processing
STATEMENT: >>>
The flash-map backend exposes one 180 KiB primary slot beginning at 0x0800C000. MCUboot receives
image-management upload chunks for image 0 and supplies slot-relative offsets to this backend.

Writes are constrained to the primary-slot bounds and require a 4-byte-aligned destination, source,
and length. The backend unlocks flash, programs 32-bit words, and locks flash after each operation.
Erasures are constrained to slot bounds and 2048-byte physical-page boundaries. Progressive erase
is enabled so MCUboot erases the pages required by the upload rather than using the retired explicit
91-page erase command.
<<<
RELATIONS:
- TYPE: Parent
  VALUE: RQ-H1FWHVPSIB-2
  ROLE: Refines
- TYPE: Parent
  VALUE: RQ-H1FWHVPSIB-3
  ROLE: Refines

[DESIGN_ITEM]
UID: SW-H1FWHVPSIB-12
TITLE: Manufacturer Hardware Abstraction
STATEMENT: >>>
The firmware integrates source code provided by the manufacturer of the microcontroller unit in
order to interface with various peripherals of the microcontroller. These include functions to
interface with the following peripherals of the microcontroller:

- UART serial port
- GPIO
- Flash memory controller
<<<
RELATIONS:
- TYPE: Parent
  VALUE: RQ-H1FWHVPSIB-1
  ROLE: Refines
- TYPE: Parent
  VALUE: RQ-H1FWHVPSIB-2
  ROLE: Refines
- TYPE: Parent
  VALUE: RQ-H1FWHVPSIB-3
  ROLE: Refines
- TYPE: Parent
  VALUE: RQ-H1FWHVPSIB-4
  ROLE: Refines

[DESIGN_ITEM]
UID: SW-H1FWHVPSIB-9
TITLE: UART3 Transport
STATEMENT: >>>
The serial bootloader uses UART3 at 38400 baud, 8 data bits, no parity, and one stop bit. Reception
is interrupt-driven one byte at a time into a 1024-byte ring buffer. The MCUboot line reader removes
bytes from the ring buffer and returns one newline-terminated NLIP line at a time. A full ring buffer
drops newly received bytes until space becomes available.

Transmission uses blocking HAL UART transmission. The upload-activity LED pattern is updated while
a line is being received and returns to the idle pattern after a complete line or receive timeout.
<<<
RELATIONS:
- TYPE: Parent
  VALUE: RQ-H1FWHVPSIB-4
  ROLE: Refines
- TYPE: Parent
  VALUE: RQ-H1FWHVPSIB-9
  ROLE: Refines

[DESIGN_ITEM]
UID: SW-H1FWHVPSIB-10
TITLE: MCUboot Serial-Management Processing
STATEMENT: >>>
MCUboot serial management uses standard NLIP line framing. Each management packet contains an SMP
header and CBOR payload, is protected by CRC16-XMODEM, base64 encoded, and divided into newline-
terminated NLIP lines. The configured maximum received management message is 512 bytes.

The enabled management operations provide echo, image status/listing, image-0 upload, and system
reset. Upload requests carry an image offset and data chunk. MCUboot validates request sequencing,
decoding, framing CRC, image bounds, and final image metadata before the image is eligible to boot.
Malformed packets receive a management error response or are discarded without transferring
execution to their contents.
<<<
RELATIONS:
- TYPE: Parent
  VALUE: RQ-H1FWHVPSIB-2
  ROLE: Refines
- TYPE: Parent
  VALUE: RQ-H1FWHVPSIB-4
  ROLE: Refines
- TYPE: Parent
  VALUE: RQ-H1FWHVPSIB-11
  ROLE: Refines

[DESIGN_ITEM]
UID: SW-H1FWHVPSIB-14
TITLE: MCUboot Bootutil Integration
STATEMENT: >>>
The firmware integrates the MCUboot bootutil library to provide industry-standard secure boot
capabilities. The bootutil module provides functions to validate application images stored in flash
memory, including verification of image headers, cryptographic signature validation, and integrity
checks. Image integrity is represented in the MCUboot TLV area rather than the legacy stored
application CRC. The bootutil library uses a single application slot architecture with primary slot
validation enabled. The firmware configures MCUboot with the following parameters:

- MCUBOOT_IMAGE_NUMBER = 1: Single application image
- MCUBOOT_SINGLE_APPLICATION_SLOT = 1: Single slot architecture
- MCUBOOT_SIGN_EC256 = 1: EC256 signature algorithm
- MCUBOOT_VALIDATE_PRIMARY_SLOT = 1: Validate primary slot on every boot
- MCUBOOT_SERIAL = 1: Serial bootloader interface enabled
- MCUBOOT_OVERWRITE_ONLY = 1: Overwrite-only image update mode
- MCUBOOT_ERASE_PROGRESSIVELY = 1: Erase pages as required during upload
- MCUBOOT_SERIAL_MAX_RECEIVE_SIZE = 512: Maximum decoded management message size
- MCUBOOT_FIH_PROFILE_OFF = 1: Fault-injection-hardening profile disabled

The bootutil library processes the application image header and TLV area to verify the image
integrity and authenticity before allowing the bootloader to jump to the application code.
<<<
RELATIONS:
- TYPE: Parent
  VALUE: RQ-H1FWHVPSIB-5
  ROLE: Refines

[DESIGN_ITEM]
UID: SW-H1FWHVPSIB-15
TITLE: Vector Table Validation
STATEMENT: >>>
Before jumping to the application, the firmware reads the stack pointer and reset handler addresses
from the application image vector table. The firmware then validates:

1. Stack Pointer: Validates that the stack pointer is within the inclusive RAM range 0x20000000
   through 0x20008000.
2. Reset Handler: Ensures the reset handler address is within the valid application code range,
   which must be greater than or equal to the image start address and less than the end of the
   current executable-image bound (0x08024000).

If either validation fails, the firmware outputs ERR_SP or ERR_RH and returns control to the
bootloader instead of jumping to the application.
<<<
RELATIONS:
- TYPE: Parent
  VALUE: RQ-H1FWHVPSIB-6
  ROLE: Refines
- TYPE: Parent
  VALUE: RQ-H1FWHVPSIB-7
  ROLE: Refines

[DESIGN_ITEM]
UID: SW-H1FWHVPSIB-17
TITLE: Serial Bootloader Interface
STATEMENT: >>>
The firmware implements a serial bootloader interface using the UART3 peripheral to allow
firmware updates via the MCUboot management protocol. After initialization and before each image
validation attempt, boot_serial_check_start() provides a three-second recovery interval.

The serial bootloader supports the following operations:
- Management echo for bootloader-presence detection
- Image status/listing
- Image-0 upload, including progressive erase and programming of application flash
- System reset

If validation fails, the main loop repeats the recovery interval indefinitely. If validation
succeeds and no recovery operation prevents boot, the firmware transfers execution to the image.
<<<
RELATIONS:
- TYPE: Parent
  VALUE: RQ-H1FWHVPSIB-4
  ROLE: Refines
- TYPE: Parent
  VALUE: RQ-H1FWHVPSIB-9
  ROLE: Refines
- TYPE: Parent
  VALUE: RQ-H1FWHVPSIB-12
  ROLE: Refines

[DESIGN_ITEM]
UID: SW-H1FWHVPSIB-18
TITLE: Application Handoff
STATEMENT: >>>
After all image and vector-table checks succeed, the bootloader disables interrupts, stops and
clears SysTick, disables and clears NVIC interrupt state, and writes the application vector-table
address to VTOR. It issues data and instruction synchronization barriers, re-enables interrupts,
loads MSP from the first vector-table word, and branches directly to the reset handler from the
second vector-table word without retaining a C call frame on the new stack.
<<<
RELATIONS:
- TYPE: Parent
  VALUE: RQ-H1FWHVPSIB-10
  ROLE: Refines

[DESIGN_ITEM]
UID: SW-H1FWHVPSIB-19
TITLE: Firmware Image Packaging and Trust
STATEMENT: >>>
The application is linked to begin at 0x0800C200. The image-generation tooling places a 512-byte
MCUboot header at the primary-slot base, adds SHA-256 metadata in the TLV area, and signs release
images using ECDSA with the NIST P-256 curve. The bootloader contains only the matching public key.

Production private keys shall be maintained outside source control in an access-controlled signing
environment. Any private key stored with development tooling shall be identified as a non-production
test key and shall not be used to authorize production firmware.
<<<
RELATIONS:
- TYPE: Parent
  VALUE: RQ-H1FWHVPSIB-1
  ROLE: Refines
- TYPE: Parent
  VALUE: RQ-H1FWHVPSIB-5
  ROLE: Refines

[DESIGN_ITEM]
UID: SW-H1FWHVPSIB-20
TITLE: Interrupted Upload Behavior
STATEMENT: >>>
The single-slot upload writes directly into the primary slot and progressively erases affected flash
pages. Until the upload contains a complete image with valid MCUboot metadata and signature,
boot_go() rejects the slot. The bootloader then remains in its recovery loop so the PC can restart or
resume a valid upload. The design does not provide rollback to the previously installed image because
there is no secondary slot.
<<<
RELATIONS:
- TYPE: Parent
  VALUE: RQ-H1FWHVPSIB-2
  ROLE: Refines
- TYPE: Parent
  VALUE: RQ-H1FWHVPSIB-3
  ROLE: Refines
- TYPE: Parent
  VALUE: RQ-H1FWHVPSIB-12
  ROLE: Refines

[[/SECTION]]

[[/SECTION]]

[DOCUMENT]
TITLE: GBSK HVPS Interface Application FW Software Design Document
UID: DHF-GBSK-0096
METADATA:
  COMPONENT: hvps-interface/main

[GRAMMAR]
IMPORT_FROM_FILE: @grammar

[[SECTION]]
TITLE: Purpose

[TEXT]
STATEMENT: >>>
The purpose of this document is to outline the design specifications of the GBSK HVPS Interface
Application Firmware.
<<<

[[/SECTION]]

[[SECTION]]
TITLE: Scope

[TEXT]
STATEMENT: >>>
This document describes the design modules and sub-modules of the GBSK HVPS Interface
Application Firmware.
The information in this document is derived from the HVPS Interface Application FW SRS, referenced in
this document.

\*The term Software applies to both Software and Firmware components.
<<<

[[/SECTION]]

[[SECTION]]
TITLE: Abbreviations and Definitions

[TEXT]
STATEMENT: >>>
FW
  Firmware

MCU
  Microcontroller Unit

PRS
  Product Requirements Specification

SDP
  Software Development Plan

SRS
  Software Requirements Specification

SW
  Software
<<<

[[/SECTION]]

[[SECTION]]
TITLE: Overview

[TEXT]
STATEMENT: >>>
The HVPS interface application firmware is used to control and receive feedback from HVPS.
The HVPS interface application firmware reports data back to and receives commands from the main
control application firmware. The HVPS interface application firmware contains routines to ramp up the
filament current, as well as the high voltage. It contains a proportional-integral feedback
controller for regulating the emission output to a given setpoint.
The HVPS interface application firmware runs on the MCU of the HVPS interface board.
Application setup and cyclic processing run in the default FreeRTOS task. External ADC result processing and feedback-control calculations run in a separate FreeRTOS control task.
<<<

[[/SECTION]]

[[SECTION]]
TITLE: References

[TEXT]
STATEMENT: >>>
DHF-GBSK-0001, Rev. 1: GBSK Software Development Plan (SDP)

DHF-GBSK-0003, Rev. 1: GBSK Software Verification Plan (SVP)

DHF-GBSK-0019, Rev. 1: GBSK HVPS Interface Application Software Requirements Specification (SRS)

DHF-GBSK-0101: GBSK HVPS Interface Application FW Verification Testing Protocol

DHF-GBSK-0031, Rev. 1: GBSK Firmware Architecture Description
<<<

[[/SECTION]]

[[SECTION]]
TITLE: Architecture Overview

[[SECTION]]
TITLE: High Level System Architecture

[TEXT]
STATEMENT: >>>
See source document DHF-GBSK-0096 for the high-level system architecture diagram.
<<<

[[/SECTION]]

[[SECTION]]
TITLE: Sequence Diagram

[TEXT]
STATEMENT: >>>
See source document DHF-GBSK-0096 for the sequence diagram.
<<<

[[/SECTION]]

[[SECTION]]
TITLE: Main Modules

[TEXT]
STATEMENT: >>>
**HVPS Communication** – The HVPS Interface interfaces with the HVPS (High Voltage Power Supply)
device itself. This interface firmware automatically controls the operation of the HVPS and monitors
feedback signals to automatically adjust output or respond to critical events such as over-temperatures
and other faults.

**Control Loop** – The control loop monitors feedback signals to automatically adjust the output and create
a stable X-Ray emission.

**Main Control Communication** – The HVPS Interface will receive both serial data signals and signal
status flags from the main control firmware. Serial data comes via RS485 protocol and signal flags by
digital logic which are ultimately interpreted using the HAL Libraries for UART and GPIO. These signals
will indicate instructions for the HVPS to run as well as fault conditions, such as interlocks and
over-temperatures. The HVPS firmware will periodically report data back to the main control firmware
approximately once per second.

**Setpoints** – discrete data points directed by the main control input for the HVPS firmware to output

**Feedback Reporting** – the HVPS firmware monitors cathode, filament, the grid, arcs, HV status, and
the Master fault and reports them back to the Main Control firmware.
<<<

[[/SECTION]]

[[SECTION]]
PREFIX: SW-H1FWHVPS-
TITLE: Design Items

[DESIGN_ITEM]
UID: SW-H1FWHVPS-106
TITLE: FTDI UART Frame Handling and Bootloader Command
STATEMENT: >>>
The firmware uses interrupt-driven UART communication to exchange framed data with the PC. It sends
one complete buffer at a time, receives data one byte at a time, and processes complete frames outside
the interrupt callback.

Each recognized command has a fixed frame length. Invalid or oversized frames reset the parser, and
reception remains available for the next valid frame. The exact seven-byte `*B00TL\n` frame causes a
system reset into the bootloader.
<<<
RELATIONS:
- TYPE: Parent
  VALUE: RQ-H1FWHVPS-19
  ROLE: Refines

[DESIGN_ITEM]
UID: SW-H1FWHVPS-107
TITLE: Internal ADC
STATEMENT: >>>
The firmware reads several feedback signals from the internal ADC peripheral. 15 of the ADC channels
are used, and they are read sequentially using the manufacturer's built in hardware abstraction
library for DMA reads of the ADC peripheral. The firmware periodically reads newly received values
before initiating a new DMA read.

The internal ADC DMA buffer is polled by the application. Half-transfer and transfer-complete
interrupts are disabled because the buffer does not require callback processing and continuous
interrupt activity could interfere with the external ADC DMA transfers. DMA transfer-error handling
remains enabled.
<<<
RELATIONS:
- TYPE: Parent
  VALUE: RQ-H1FWHVPS-5
  ROLE: Refines
- TYPE: Parent
  VALUE: RQ-H1FWHVPS-12
  ROLE: Refines
- TYPE: Parent
  VALUE: RQ-H1FWHVPS-13
  ROLE: Refines
- TYPE: Parent
  VALUE: RQ-H1FWHVPS-14
  ROLE: Refines

[DESIGN_ITEM]
UID: SW-H1FWHVPS-108
TITLE: Control Communication Interface
STATEMENT: >>>
The firmware communicates with the main control board via one of the microcontroller's serial UART
interfaces. The firmware both receives and transmits data on this UART port. Due to the nature of
UART having independent transmit and receive lines, the transmit and receive functionality operate
independently. As the UART baud rate is relatively slow compared to the processing speed of the
microcontroller, both sending and receiving data is performed with nonblocking interrupt callback
functions.

Transmitted data is sent as a buffer of bytes, representing a singular data packet to the PC, with
the interrupt callback occurring once all data bytes have been transmitted. The firmware sets a flag
when transmission is initiated, and clears the flag after transmission is finished, to not create
transmission conflicts on the transmit line.

Reception is performed one byte at a time, with the interrupt callback occurring once a data byte is
available. The parsing of the received byte is done to determine whether a complete data packet has
been received from the PC, as according to the communication protocol. Once a completed data packet
has been received, the firmware sets a flag for further data processing outside of the parsing
inside of the interrupt callback.

As transmission on UART is asynchronous both in terms of clock as well as word alignment (within a
packet), a 'sync value' is utilized at the start of each packet to help synchronize communication in
case of any lost or missing bytes.
<<<
RELATIONS:
- TYPE: Parent
  VALUE: RQ-H1FWHVPS-4
  ROLE: Refines

[DESIGN_ITEM]
UID: SW-H1FWHVPS-109
TITLE: Control Communication Data
STATEMENT: >>>
The data received from the main control board are commands to set various output control parameters
including grid voltage, filament current, high voltage, and output power. There are also commands to
initiate the process to test the high voltage and grid interlocks that the main control board
provides to the firmware.

The transmitted data to the main control board are the target setpoint values for, as well as the
monitored feedback values from, the HVPS. Additionally, status flags and IO values are reported by
the firmware.
<<<
RELATIONS:
- TYPE: Parent
  VALUE: RQ-H1FWHVPS-2
  ROLE: Refines
- TYPE: Parent
  VALUE: RQ-H1FWHVPS-5
  ROLE: Refines
- TYPE: Parent
  VALUE: RQ-H1FWHVPS-8
  ROLE: Refines

[DESIGN_ITEM]
UID: SW-H1FWHVPS-110
TITLE: External ADC Communication
STATEMENT: >>>
The firmware communicates with two external ADC IC chips. Each chip has one channel, and they are
responsible for reading the mA and kV feedback signals. Each chip uses a dedicated SPI bus and chip
select line, and both SPI buses operate at 2.25 Mbit/s.

The external ADC module starts a 16-pair burst every 5 ms and acquires both channels using
nonblocking SPI receive DMA transfers. Each received frame is decoded and checked for valid device
framing. At 2 ms after the burst starts, an incomplete or missing result is rejected as an
acquisition-timing error. DMA or framing errors also produce an invalid result and prevent that
result from being used for feedback processing.

The 16 samples from each channel are averaged. The averaged 16-bit codes are converted to engineering
units using the 4.096 V ADC reference and the channel input scaling: a 20 kOhm/10 kOhm divider and
0.1 V/kV for high voltage, and a 30 kOhm/20 kOhm divider and 1 V/mA for cathode current. The paired
result is then published to the feedback and control functions. The ADC chip-select signals remain
inactive while the ADCs are idle.
<<<
RELATIONS:
- TYPE: Parent
  VALUE: RQ-H1FWHVPS-10
  ROLE: Refines
- TYPE: Parent
  VALUE: RQ-H1FWHVPS-11
  ROLE: Refines

[DESIGN_ITEM]
UID: SW-H1FWHVPS-111
TITLE: External DAC communication
STATEMENT: >>>
The firmware communicates with four external DAC IC chips. Each chip has one channel each and are
responsible for setting the grid voltage control signal, filament current control signal, high
voltage control signal, and emission current limit control signal. All DAC chips are identical make
and model, and the firmware communicates with all chips on a singular SPI bus, using independent
chip select signals for each chip. The external DAC module waits for any queued-up requests by the
rest of the firmware to write new DAC values. In case multiple DAC values are queued up simultaneous
or in quick succession, the DAC module processes them in FIFO (first in first out) fashion, waiting
for the SPI bus to be free until the next value is processed.

The DAC module utilizes the manufacturer's hardware abstraction library to write serial data to the
SPI bus. The writes to the SPI bus are non-block interrupt-based calls which allows the processor to
continue operating during the relatively longer SPI transmission (compared to processing speed). The
DAC module utilizes the SPI interrupt handler to set flags for handling the queued DAC requests
(indicating bus is free).

In addition to sending data over the SPI bus, the DAC module handles the four independent digital
chip-select outputs through the hardware abstraction library's GPIO control. All four outputs
initialize inactive high and remain high whenever no DAC transaction is active.
<<<
RELATIONS:
- TYPE: Parent
  VALUE: RQ-H1FWHVPS-14
  ROLE: Refines

[DESIGN_ITEM]
UID: SW-H1FWHVPS-112
TITLE: Input Debouncing
STATEMENT: >>>
The digital inputs are debounced by sampling the state of the input signals every time a processing
flag gets set. This processing flag is set every 1 msec. Once an input displays a toggled value, the
firmware begins a debounce countdown. During this debounce period, any bouncing signals are ignored.
After the debounce period is over, the firmware checks to see if the input truly did toggle or if it
was just noise. If the signal indicates a 'true' toggle, the firmware updates the changed input
states for processing as well as reporting to the main control application firmware.
<<<
RELATIONS:
- TYPE: Parent
  VALUE: RQ-H1FWHVPS-5
  ROLE: Refines
- TYPE: Parent
  VALUE: RQ-H1FWHVPS-14
  ROLE: Refines

[DESIGN_ITEM]
UID: SW-H1FWHVPS-113
TITLE: Interlock Enable
STATEMENT: >>>
The firmware monitors the interlock signals coming from the main control board. These signals can
independently, from the HVPS interface microcontroller, disable emission. However, for redundancy,
the firmware will also disable its own outputs to the HVPS to terminate emission if it detects that
the interlock signals are requesting to disable emission.

Additionally, the firmware will proceed to 'lock' its own emission output controls and disallow
emission until the main control board sends commands to unlock the controls. The unlock sequence
requires that the main control board send these commands while the interlocks are specifically in a
'disabled' state and then toggle the interlocks into an 'enable' state within a certain time period.
This is to ensure that the hardware signals are functioning as the firmware expects and are able to
disable emission if needed. This lock and unlock process is required for both the high voltage
interlock and grid interlock signals coming from the main control board.
<<<
RELATIONS:
- TYPE: Parent
  VALUE: RQ-H1FWHVPS-14
  ROLE: Refines

[DESIGN_ITEM]
UID: SW-H1FWHVPS-114
TITLE: HVPS Interface Status Flags
STATEMENT: >>>
The firmware tracks Boolean status flags in a bitmask reported to the main control board. The
following operating-state flags are monitored and reported:

- HV interlock control enabled
- Grid interlock control enabled
- Filament ramp in progress
- High voltage ramp in progress
- Emission ongoing
- Configuration modification unlocked
- Emission-current controller enabled
- Fast filament ramping enabled

The firmware also reports a distinct latched status flag for each of these HVPS fault sources:

- Filament clock fault
- Cathode arc
- Fan fault
- 24 V overcurrent
- Master fault
- High-voltage overcurrent
- Temperature 1 fault
- Cathode overcurrent
- Temperature 3 fault
- Temperature 2 fault

When a monitored fault input becomes active, the firmware sets the corresponding status flag and
writes a diagnostic entry identifying the fault source and its status and input bit positions.
Deasserting the input does not clear the flag. An explicit fault clear removes the corresponding
latched flag and writes a diagnostic fault-cleared entry.
<<<
RELATIONS:
- TYPE: Parent
  VALUE: RQ-H1FWHVPS-5
  ROLE: Refines
- TYPE: Parent
  VALUE: RQ-H1FWHVPS-14
  ROLE: Refines

[DESIGN_ITEM]
UID: SW-H1FWHVPS-115
TITLE: Output Power
STATEMENT: >>>
The output power is set by the main control board via commands to the firmware. The firmware
uses the power setpoint and high-voltage setpoint to derive the target emission current as power
divided by voltage for the proportional-integral grid controller.
<<<
RELATIONS:
- TYPE: Parent
  VALUE: RQ-H1FWHVPS-8
  ROLE: Refines

[DESIGN_ITEM]
UID: SW-H1FWHVPS-116
TITLE: High Voltage Output and Ramping
STATEMENT: >>>
When a target high-voltage value is requested while the high-voltage control is unlocked, the
firmware sets the high-voltage-ramping status and ramps the command toward the target while emission
is inactive. Each 5 ms feedback-control cycle scales the command increment by the elapsed 0.005 s
rather than treating the configured ramp values as per-cycle steps.

The default slow and fast ramp rates are 5 kV/s and 20 kV/s. For either ramp direction, an error
whose magnitude is less than 5 kV uses the slow rate, an error from 5 kV to 20 kV uses four times the
slow rate, and an error of at least 20 kV uses the fast rate. With the defaults, these produce
0.025 kV and 0.1 kV changes per 5 ms cycle. The command is limited to the configured 0 kV to 100 kV
output range.

After the feedback reaches the target, feedback samples within +/-2% of the requested voltage add
5 ms to an elapsed stability accumulator. The firmware clears the high-voltage-ramping status after
the accumulator reaches 4000 ms; samples outside the tolerance do not add to the accumulator. If an
increasing command has reached at least 50 kV and exceeds feedback by more than 50 kV, the firmware
sets the command to zero and cancels the ramp.
<<<
RELATIONS:
- TYPE: Parent
  VALUE: RQ-H1FWHVPS-8
  ROLE: Refines
- TYPE: Parent
  VALUE: RQ-H1FWHVPS-14
  ROLE: Refines

[DESIGN_ITEM]
UID: SW-H1FWHVPS-117
TITLE: Filament Output and Ramping
STATEMENT: >>>
When a target filament-current value is requested, the firmware starts the warming status and
services the ramp every 3 ms while warming is active and emission is inactive. Each active upward
ramp adds 2.25 mA, which is the elapsed-time increment for the fixed 750 mA/s ramp rate. The active
command is limited to the configured minimum and maximum filament-current values. An invalid target
or command outside the configured range sets the target and command to zero and cancels warming.

When feedback has reached the target, each sample from the target through 2% above the target adds
3 ms to the stability accumulator. The firmware clears warming after at least 4000 ms of qualifying
samples. Feedback more than 2% above the target makes the command equal the target without adding
stability time.

While feedback remains below the target, a commanded current at or above the configured minimum that exceeds
feedback by more than 300 mA adds 3 ms to a feedback-discrepancy accumulator. At 6000 ms of
qualifying samples, the firmware sets the filament command to zero and cancels warming.
<<<
RELATIONS:
- TYPE: Parent
  VALUE: RQ-H1FWHVPS-6
  ROLE: Refines
- TYPE: Parent
  VALUE: RQ-H1FWHVPS-17
  ROLE: Refines

[DESIGN_ITEM]
UID: SW-H1FWHVPS-118
TITLE: Grid Output
STATEMENT: >>>
The firmware accepts a direct adjustment-grid command from the main control board and writes values
from zero through the configured maximum to the external grid DAC. While emission-current grid
control is enabled during emission, the feedback controller supersedes the direct command and
updates the grid output within its configured control limits and elapsed-time slew rates.
<<<
RELATIONS:
- TYPE: Parent
  VALUE: RQ-H1FWHVPS-7
  ROLE: Refines
- TYPE: Parent
  VALUE: RQ-H1FWHVPS-14
  ROLE: Refines

[DESIGN_ITEM]
UID: SW-H1FWHVPS-119
TITLE: Emission Limit Output
STATEMENT: >>>
The emission current limit signal is set to a fixed output value
<<<
RELATIONS:
- TYPE: Parent
  VALUE: RQ-H1FWHVPS-9
  ROLE: Refines

[DESIGN_ITEM]
UID: SW-H1FWHVPS-120
TITLE: Emission Current Grid Control
STATEMENT: >>>
Grid control is enabled by default and operates only while x-ray emission is active. The requested
emission current is the requested power divided by the requested high voltage. On activation, the
firmware initializes the adjustment-grid command to its configured maximum of 600 units, clears the
integral state, and runs the proportional-integral calculation from the 5 ms external-feedback
control task.

The controller error is requested cathode current minus measured cathode current. The default
proportional gain is -25 for requested high voltage at or below 50 kV, -35 above 50 kV through
70 kV, and -150 above 70 kV. The integral time is 0.2 s, and each integral increment is calculated
as `(Kp / 0.2 s) * 0.005 s * error`. The firmware compensates the integral state when the gain or
maximum-grid feedforward changes. When the absolute error is within 1% of the absolute requested
current, the controller holds the command and integral state and does not issue a DAC write.

Outside the hold band, the default downward and upward slew limits are 3000 and 1000 grid units per
second, respectively, yielding a reachable range of 15 units down and 5 units up per control cycle.
The command is clamped to both this per-cycle range and the configured 50-to-600-unit output range.
The integral candidate is accepted only when the unsaturated command is inside the reachable range
or when the integral increment unwinds a saturation condition. Disabling grid control or ending
emission restores the maximum-grid command and clears the controller state.
<<<
RELATIONS:
- TYPE: Parent
  VALUE: RQ-H1FWHVPS-14
  ROLE: Refines

[DESIGN_ITEM]
UID: SW-H1FWHVPS-121
TITLE: DMA Grid Clock
STATEMENT: >>>
The HVPS requires a toggling grid clock signal to allow emission. The firmware uses a timer update
event and DMA to write alternating set and reset values to the grid-clock GPIO output. This produces
the grid-clock waveform without a timer interrupt handler.

Enabling the clock resets the output low, initializes the DMA transfer, and starts the timer.
Disabling the clock stops the timer and DMA transfer and leaves the output low.
<<<
RELATIONS:
- TYPE: Parent
  VALUE: RQ-H1FWHVPS-1
  ROLE: Refines

[DESIGN_ITEM]
UID: SW-H1FWHVPS-122
TITLE: External Feedback Control Task
STATEMENT: >>>
The firmware creates a dedicated FreeRTOS task for external ADC result processing and feedback
control. The periodic external ADC completion check notifies the task once per 5 ms acquisition
period. A valid result replaces the high-voltage and cathode-current feedback values; invalid
results do not replace feedback. Each notification then processes the high-voltage ramp and
emission-current grid controller using the current feedback.

High-voltage increments, grid-controller integration, and grid-command slew are each multiplied by
the 0.005 s control period. Their behavior therefore follows configured rates and time constants
rather than a fixed change per task invocation. Shared status and controller state are protected
while accessed by the task and interrupt context. DAC writes are performed outside the protected
state-processing region so external feedback processing does not block communication, I/O, or DAC
servicing.
<<<
RELATIONS:
- TYPE: Parent
  VALUE: RQ-H1FWHVPS-10
  ROLE: Refines
- TYPE: Parent
  VALUE: RQ-H1FWHVPS-11
  ROLE: Refines
- TYPE: Parent
  VALUE: RQ-H1FWHVPS-14
  ROLE: Refines

[DESIGN_ITEM]
UID: SW-H1FWHVPS-35
TITLE: Manufacturer Hardware Abstraction
STATEMENT: >>>
The firmware integrates source code provided by the manufacturer of the microcontroller unit to
interface with various peripherals of the microcontroller. These include functions to interface with
the following peripherals of the microcontroller:

- UART serial port
- GPIO
- SPI serial port
- Flash memory controller
- ADC peripheral
- Timer peripheral
<<<
RELATIONS:
- TYPE: Parent
  VALUE: RQ-H1FWHVPS-2
  ROLE: Refines
- TYPE: Parent
  VALUE: RQ-H1FWHVPS-4
  ROLE: Refines
- TYPE: Parent
  VALUE: RQ-H1FWHVPS-5
  ROLE: Refines
- TYPE: Parent
  VALUE: RQ-H1FWHVPS-6
  ROLE: Refines
- TYPE: Parent
  VALUE: RQ-H1FWHVPS-7
  ROLE: Refines
- TYPE: Parent
  VALUE: RQ-H1FWHVPS-8
  ROLE: Refines
- TYPE: Parent
  VALUE: RQ-H1FWHVPS-9
  ROLE: Refines
- TYPE: Parent
  VALUE: RQ-H1FWHVPS-10
  ROLE: Refines
- TYPE: Parent
  VALUE: RQ-H1FWHVPS-11
  ROLE: Refines
- TYPE: Parent
  VALUE: RQ-H1FWHVPS-12
  ROLE: Refines
- TYPE: Parent
  VALUE: RQ-H1FWHVPS-13
  ROLE: Refines

[DESIGN_ITEM]
UID: SW-H1FWHVPS-36
TITLE: Input Signals
STATEMENT: >>>
The firmware logs several digital input signals coming from the HVPS and monitors them to determine
whether an HVPS fault has occurred. OC_CAT is handled separately from the active-high fault inputs:
a low level on the initial input sample and each subsequent high-to-low transition reports the
cathode-overcurrent fault.

The firmware also monitors three digital inputs from the main control board for enabling and
disabling emission: HV interlock, grid interlock, and the emission start signal.
<<<
RELATIONS:
- TYPE: Parent
  VALUE: RQ-H1FWHVPS-5
  ROLE: Refines
- TYPE: Parent
  VALUE: RQ-H1FWHVPS-14
  ROLE: Refines

[DESIGN_ITEM]
UID: SW-H1FWHVPS-37
TITLE: Output Signals
STATEMENT: >>>
The firmware controls various digital output signals. There are grid clocks and watchdog reset
signals which are toggled periodically by the firmware. Additionally, there are three digital
control signals which disable output on the HVPS: grid allowed, PFC allowed, and HV allowed. These
three signals correspond to three signals on the HVPS which similarly are used to disallow grid
switching, PFC enabling, and HV enabling on the HVPS. All these signals need to be appropriately
asserted for emission output to be enabled.
<<<
RELATIONS:
- TYPE: Parent
  VALUE: RQ-H1FWHVPS-14
  ROLE: Refines

[DESIGN_ITEM]
UID: SW-H1FWHVPS-123
TITLE: Logging Module
STATEMENT: >>>
The compile-time logging switch defaults to enabled with DEBUG as the highest included severity.
Initialization binds output to USART3, enables the runtime switch, and clears a 1024-byte transmit ring
buffer. ERROR, WARN, INFO, and DEBUG calls format severity-tagged records in a 256-byte working buffer,
truncate oversized records to leave room for a CRLF terminator, and enqueue them for FTDI_TX. Startup
emits an INFO record containing `Sensus setup complete`. Unprefixed formatted output and newline-delimited
JSON status containing `runtime_ms`, `sys_stat`, and `sys_io_bits` use the same queue and runtime switch;
the optional 500 ms periodic status task is disabled by default. The UART interrupt starts one-byte
transmission and each transmit-complete callback drains the next queued byte. Writers briefly mask
interrupts while copying bytes; if the ring buffer fills, they drop the remainder instead of waiting.
Runtime-disabled logging returns before formatting or enqueueing output. The USART3 error callback
clears UART error flags so subsequent transmission can proceed.

After input debouncing identifies a transition, the HV interlock handler emits WARN records
containing `Hv int rose` or `Hv int fell`, the grid interlock handler emits `Grid int rose`
or `Grid int fell`, and the beam-control handler emits `Beam ctrl rose` or
`Beam ctrl fell`.
<<<
RELATIONS:
- TYPE: Parent
  VALUE: RQ-H1FWHVPS-18
  ROLE: Refines

[DESIGN_ITEM]
UID: SW-H1FWHVPS-124
TITLE: FTDI Configuration GET and SET Commands
STATEMENT: >>>
The firmware recognizes an 11-byte GET frame consisting of the `*GET..` command, a little-endian
16-bit parameter-category identifier, a little-endian 16-bit parameter index, and a newline
terminator. For a supported configuration-value category and index, GET reads the selected value and
returns a 15-byte response containing `*GET..`, the received category and index, the value as a
little-endian IEEE-754 32-bit float, and a newline terminator. The firmware recognizes a 15-byte SET
frame consisting of the `*..SET` command, the same category and index fields, a little-endian
IEEE-754 32-bit float value, and a newline terminator. A supported SET updates the selected
configuration value and returns the corresponding 15-byte `*..SET` confirmation frame. Requests
with an unrecognized command header or unsupported category, SET requests outside the configuration
table, and requests with an index of 64 or greater are ignored without response.
<<<
RELATIONS:
- TYPE: Parent
  VALUE: RQ-H1FWHVPS-19
  ROLE: Refines

[DESIGN_ITEM]
UID: SW-H1FWHVPS-125
TITLE: FTDI Bulk-Read Commands
STATEMENT: >>>
The firmware recognizes the seven-byte `*ACFGS\n`, `*ASPTS\n`, and `*AFBVS\n` bulk-read requests
by their five-character command and expected frame length. In one response, the firmware echoes
`*` and the request command, appends every value from the requested category as consecutive
little-endian IEEE-754 32-bit floats in increasing index order, and appends a newline terminator.
`ACFGS` returns all 32 configuration values in a 135-byte response, `ASPTS` returns all six
setpoints in a 31-byte response, and `AFBVS` returns all five feedback values in a 27-byte
response. An unrecognized command header is discarded without response.
<<<
RELATIONS:
- TYPE: Parent
  VALUE: RQ-H1FWHVPS-19
  ROLE: Refines

[DESIGN_ITEM]
UID: SW-H1FWHVPS-126
TITLE: Firmware Version Response
STATEMENT: >>>
The control-command processor recognizes command value ``0x7F`` as a version request. It
queues a 13-word UART response containing two synchronization words, the ``VRSN`` marker,
the operating-mode identifier, the null-padded release version string in a 32-byte field,
and an additive checksum. The response is sent when the UART transmitter is available,
ahead of the next periodic telemetry frame.
<<<
RELATIONS:
- TYPE: Parent
  VALUE: RQ-H1FWHVPS-20
  ROLE: Refines

[[/SECTION]]

[[/SECTION]]

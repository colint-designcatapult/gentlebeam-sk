[DOCUMENT]
TITLE: GBSK HVPS Interface Application FW Verification Testing Protocol
UID: DHF-GBSK-0101

[GRAMMAR]
IMPORT_FROM_FILE: @grammar

[[SECTION]]
TITLE: Purpose

[TEXT]
STATEMENT: >>>
This document provides the full test protocol (a full collection of test cases) for the HVPS Interface
Application Firmware for the GBSK 1.0 system.
<<<

[[/SECTION]]

[[SECTION]]
TITLE: Scope

[TEXT]
STATEMENT: >>>
This report contains a detailed test description to conduct verification testing of GBSK 1.0 HVPS
Interface Application Firmware that covers GBSK HVPS Interface Application FW SRS.
<<<

[[/SECTION]]

[[SECTION]]
TITLE: Abbreviations and Definitions

[TEXT]
STATEMENT: >>>
FW
  Firmware

HVPS
  High Voltage Power Supply

SDP
  Software Development Plan

SVP
  Software Verification Plan

SW
  Software
<<<

[[/SECTION]]

[[SECTION]]
TITLE: References

[TEXT]
STATEMENT: >>>
DHF-GBSK-0001, Rev. 1: GBSK SDP

DHF-GBSK-0003, Rev. 1: GBSK SVP

[LINK: DHF-GBSK-0019]

[LINK: DHF-GBSK-0096]

DHF-GBSK-0031, Rev. 1: GBSK Firmware Architecture Description
<<<

[[/SECTION]]

[[SECTION]]
TITLE: Prerequisites

[TEXT]
STATEMENT: >>>
**Pre-Execution Approval**

A Pre-Execution meeting shall take place, and approved by the project manager and QA/RA.

**Objective(s)**

Verify that:

* All software, firmware, hardware, and test equipment version configurations are identified and listed in the test report prior to execution.
* Test personnel is assigned and available.

**Assumptions & Constraints**

None

**Acceptance Criteria**

All objectives met; test execution can start.
<<<

[[/SECTION]]

[[SECTION]]
PREFIX: TC-H1FWHVPS-
TITLE: Test Protocol

[TEST_CASE]
UID: TC-H1FWHVPS-18
TITLE: Grid control clock - Test Case
STATEMENT: >>>
The firmware shall generate a stable grid control clock within the frequency
range specified by the SRS and shall leave the grid-clock output inactive when
the clock is disabled.
<<<
PREREQUISITES: >>>
* The system is powered on and ready to use.
* A treatment plan should be ready to load.
* An oscilloscope or logic analyzer is connected to the grid-clock output.
<<<
STEPS: >>>
1. Power on the system.
2. Load a treatment plan.
3. Observe the grid-clock output with the measurement instrument.
4. Measure the grid-clock frequency.
5. Disable the grid clock using the approved service or test control.
6. Observe the grid-clock output after disabling it.
7. Re-enable the grid clock and observe the output.
<<<
EXPECTED_BEHAVIOR: >>>
1. Verify the system is powered on successfully.
2. Verify the plan is loaded successfully.
3. Verify the grid-clock output is present when enabled.
4. Verify the measured frequency is between 1 kHz and 20 kHz.
5. Verify the clock stops when disabled.
6. Verify the output remains inactive after disabling the clock.
7. Verify the clock restarts cleanly when re-enabled.
<<<
RELATIONS:
- TYPE: Parent
  VALUE: RQ-H1FWHVPS-1
  ROLE: Verifies

[TEST_CASE]
UID: TC-H1FWHVPS-19
TITLE: Elapsed-time high-voltage regulation - Test Case
STATEMENT: >>>
Verify that high-voltage closed-loop commands use elapsed-time ramp rates, bounded output, feedback
stability timing, and feedback-discrepancy cancellation.
<<<
PREREQUISITES: >>>
* The system is powered on with high-voltage control unlocked and emission inactive.
* An HVPS test fixture can control high-voltage feedback independently of the requested setpoint.
* An approved diagnostic trace can capture requested voltage, feedback, DAC command,
  high-voltage-ramping status, and timestamps with at most 1 ms resolution.
* The default high-voltage configuration values are loaded.
<<<
STEPS: >>>
1. Request increasing and decreasing high-voltage targets while using the fixture to produce
   absolute feedback errors below 5 kV, from 5 kV through less than 20 kV, and at least 20 kV.
2. Capture consecutive high-voltage commands and their timestamps in each error band.
3. Drive feedback through the requested target, then supply samples within +/-2% interspersed with
   samples outside that tolerance, and observe the high-voltage-ramping status immediately before
   and after 4000 ms of accumulated in-tolerance sample time.
4. Request values that exercise the lower and configured 100 kV upper command limits.
5. During an increasing ramp, hold feedback so the command is at least 50 kV and exceeds feedback by
   more than 50 kV.
<<<
EXPECTED_BEHAVIOR: >>>
1. Verify the firmware evaluates the ramp on the 5 ms feedback-control cadence in both directions.
2. Verify the default command changes by 0.025 kV per cycle below 5 kV error and 0.1 kV per cycle in
   both larger error bands, corresponding to 5 kV/s and 20 kV/s elapsed-time rates.
3. Verify only samples within +/-2% add 5 ms to stability time, the ramping status remains set
   before the accumulator reaches 4000 ms, and the status clears on the first sample at or above
   that threshold.
4. Verify the command never falls below 0 kV or exceeds the configured 100 kV maximum.
5. Verify the feedback-discrepancy condition sets the command to zero and clears the ramping status.
<<<
RELATIONS:
- TYPE: Parent
  VALUE: RQ-H1FWHVPS-8
  ROLE: Verifies
- TYPE: Parent
  VALUE: RQ-H1FWHVPS-11
  ROLE: Verifies
- TYPE: Parent
  VALUE: RQ-H1FWHVPS-14
  ROLE: Verifies

[TEST_CASE]
UID: TC-H1FWHVPS-20
TITLE: Main control reporting - Test Case
STATEMENT: >>>
When the system is powered on, LED4 on mainboard should pulse at a rate much faster than
1 Hz.
<<<
PREREQUISITES: >>>
* The system is powered on and ready to use.
* The silkscreen reference for LED4 is DS2206
<<<
STEPS: >>>
1. Power on the system.
2. Check LED4 on the Main Board.
3. Measure the pulsing of the LED4 on the Main board.
<<<
EXPECTED_BEHAVIOR: >>>
1. Verify the system is powered on successfully.
2. Verify it's pulsing.
3. Verify it's pulsing at a rate much faster than 1 Hz.
<<<
RELATIONS:
- TYPE: Parent
  VALUE: RQ-H1FWHVPS-4
  ROLE: Verifies

[TEST_CASE]
UID: TC-H1FWHVPS-21
TITLE: HVPS digital status signals - Test Case
STATEMENT: >>>
Verify that the firmware reports HVPS digital signals, reports a distinct latched status for each
monitored fault source, and interprets the OC_CAT fault input as active-low both during startup and
during operation.
<<<
PREREQUISITES: >>>
* The system is connected to a test fixture capable of holding or toggling each HVPS fault input.
* The user of the system has service-user access.
* A treatment plan is ready to load.
* The service screen and an approved fault report or diagnostic trace are available.
* The approved clear-fault control is available.
<<<
STEPS: >>>
1. Hold all HVPS fault inputs inactive and power on the system.
2. Open the service screen.
3. Record the reported HVPS digital status before emission.
4. Load a treatment plan and record the reported HVPS digital status during emission.
5. In turn, assert the FIL_CLK, CAT_ARC, FAN, OC_24, MASTER, OC_HV, TEMP_1, TEMP_3, and TEMP_2
   fault inputs, observe the report or diagnostic trace, and then deassert each input.
6. After each input is deasserted, record its reported fault status.
7. Use the approved clear-fault control and observe the fault status and diagnostic trace.
8. Confirm that OC_CAT is high, drive it from high to low, observe the report, and then return it
   high.
9. Record the cathode-overcurrent fault status after OC_CAT returns high.
10. Clear the reported fault.
11. Power off the system, hold OC_CAT low, and power on the system again.
12. Observe the fault report or diagnostic trace produced during startup.
<<<
EXPECTED_BEHAVIOR: >>>
1. Verify the system starts successfully with no fault status reported while the inputs are
   inactive.
2. Verify the service screen is displayed.
3. Verify the reported HVPS status indicates no high voltage before emission.
4. Verify the plan loads and the reported HVPS status indicates high voltage during emission.
5. Verify each asserted active-high source sets its own status bit and produces a diagnostic entry
   identifying that source and its status and input bit positions.
6. Verify each fault status remains latched after its input is deasserted.
7. Verify the explicit clear removes all latched fault flags and produces a diagnostic cleared entry
   for each cleared source.
8. Verify the high-to-low transition is interpreted as OC_CAT assertion and reports a distinct
   cathode-overcurrent fault.
9. Verify the cathode-overcurrent status remains latched after OC_CAT is deasserted.
10. Verify the cathode-overcurrent status clears.
11. Verify the low startup level is interpreted as OC_CAT assertion.
12. Verify a cathode-overcurrent fault is reported during initial input sampling.
<<<
RELATIONS:
- TYPE: Parent
  VALUE: RQ-H1FWHVPS-5
  ROLE: Verifies

[TEST_CASE]
UID: TC-H1FWHVPS-22
TITLE: Filament current setpoint - Test Case
STATEMENT: >>>
When the system is powered, the service user should check the reported value of filament current
in the Service screen with / without a running treatment plan.
<<<
PREREQUISITES: >>>
* The system is powered on and ready to use.
* The user of the system needs to be a service user.
* A treatment plan should be ready to load.
<<<
STEPS: >>>
1. Power on the system.
2. Click Services symbol in the left side of the screen.
3. Look for value of filament current in the service screen.
4. Load a treatment plan.
5. Check the status of the system.
6. Look for value of filament current in the service screen.
<<<
EXPECTED_BEHAVIOR: >>>
1. Verify the system is powered on successfully.
2. Verify the service screen displayed.
3. Record the value and verify the output control signal of the filament current is provided by firmware application.
4. Verify the plan is loaded successfully.
5. Verify the status of the system is ready.
6. Record the value and verify the output control signal of the filament current is provided by firmware application.
<<<
RELATIONS:
- TYPE: Parent
  VALUE: RQ-H1FWHVPS-6
  ROLE: Verifies

[TEST_CASE]
UID: TC-H1FWHVPS-23
TITLE: Adjustment grid setpoint - Test Case
STATEMENT: >>>
When the system is powered, the service user should check the reported value of adjustment grid
voltage in the Service screen with / without a running treatment plan.
<<<
PREREQUISITES: >>>
* The system is powered on and ready to use.
* The user of the system needs to be a service user.
* A treatment plan should be ready to load.
<<<
STEPS: >>>
1. Power on the system.
2. Click Services symbol in the left side of the screen.
3. Look for value of adjustment grid voltage in the service screen.
4. Load a treatment plan.
5. Check the status of the system.
6. Look for value of adjustment grid voltage in the service screen.
<<<
EXPECTED_BEHAVIOR: >>>
1. Verify the system is powered on successfully.
2. Verify the service screen displayed.
3. Record the value and verify the output control signal of the adjustment grid voltage is provided by firmware application.
4. Verify the plan is loaded successfully.
5. Verify the status of the system is ready.
6. Record the value and verify the output control signal of the adjustment grid voltage is provided by firmware application.
<<<
RELATIONS:
- TYPE: Parent
  VALUE: RQ-H1FWHVPS-7
  ROLE: Verifies

[TEST_CASE]
UID: TC-H1FWHVPS-24
TITLE: High voltage setpoint 2 - Test Case
STATEMENT: >>>
When the system is powered, the service user should check the reported value of high voltage
which should be > 10 kV with loaded treatment plan.
<<<
PREREQUISITES: >>>
* The system is powered on and ready to use.
* A treatment plan should be ready to load.
<<<
STEPS: >>>
1. Power on the system.
2. Load a treatment plan.
3. Check the status of the system.
4. Look for value of the reported high voltage.
<<<
EXPECTED_BEHAVIOR: >>>
1. Verify the system is powered on successfully.
2. Verify the plan is loaded successfully.
3. Verify the status of the system is ready.
4. Record the value and verify the value of the reported high voltage is greater than 10 kV.
<<<
RELATIONS:
- TYPE: Parent
  VALUE: RQ-H1FWHVPS-8
  ROLE: Verifies

[TEST_CASE]
UID: TC-H1FWHVPS-25
TITLE: Cathode current limiter setpoint - Test Case
STATEMENT: >>>
When user powered on the system, load and run a 20 second treatment plan, verify the treatment
plan run and finished without any types of faults.
<<<
PREREQUISITES: >>>
* The system is powered on and ready to use.
* A treatment plan should be ready to load.
<<<
STEPS: >>>
1. Power on the system.
2. Load a 20 second treatment plan.
3. Start to run the loaded plan.
4. Wait for 20 seconds.
5. Click Logs symbol in the left panel of the screen.
6. Check the logs of the running treatment plan.
<<<
EXPECTED_BEHAVIOR: >>>
1. Verify the system is powered on successfully.
2. Verify the plan is loaded successfully.
3. Verify the emission and run is started successfully without any issues.
4. Verify the running of the plan is finished without any issues.
5. Verify the logs displayed in the middle of the screen.
6. Verify there is not any error or emission current fault in the logs related to the latest run of the loaded treatment plan. Also, verify there is not any kV output fault in the logs.
<<<
RELATIONS:
- TYPE: Parent
  VALUE: RQ-H1FWHVPS-9
  ROLE: Verifies

[TEST_CASE]
UID: TC-H1FWHVPS-26
TITLE: Cathode current feedback - Test Case
STATEMENT: >>>
When user powered on the system, load and run a 20 second treatment plan, verify user can
record the emission/cathode current value at approximately 5 seconds and approximately 15
seconds which is provided by firmware application.
<<<
PREREQUISITES: >>>
* The system is powered on and ready to use.
* A treatment plan should be ready to load.
<<<
STEPS: >>>
1. Power on the system.
2. Load a 20 second treatment plan.
3. Start the emission.
4. Wait for 5 seconds.
5. Wait another 10 seconds.
<<<
EXPECTED_BEHAVIOR: >>>
1. Verify the system is powered on successfully.
2. Verify the plan is loaded successfully.
3. Verify the emission started.
4. Record the emission/cathode current which is provided by firmware application.
5. Record the emission/cathode current which is provided by firmware application.
<<<
RELATIONS:
- TYPE: Parent
  VALUE: RQ-H1FWHVPS-10
  ROLE: Verifies

[TEST_CASE]
UID: TC-H1FWHVPS-27
TITLE: High voltage feedback - Test Case
STATEMENT: >>>
When user loads a treatment plan and it is ready for running, make sure the firmware provides and
sets the value of the reported high voltage.
<<<
PREREQUISITES: >>>
* The system is powered on and ready to run any treatment plan.
* A treatment plan is ready to load into the system.
<<<
STEPS: >>>
1. Power on the system.
2. Load a treatment plan.
3. Check the state of the system.
4. Check the value of the reported high voltage.
<<<
EXPECTED_BEHAVIOR: >>>
1. Verify the system is powered on successfully.
2. Verify the plan is loaded successfully.
3. Verify its state is Ready.
4. Record the value and verify it's within 10% of loaded treatment target.
<<<
RELATIONS:
- TYPE: Parent
  VALUE: RQ-H1FWHVPS-11
  ROLE: Verifies

[TEST_CASE]
UID: TC-H1FWHVPS-28
TITLE: Adjustment grid voltage feedback - Test Case
STATEMENT: >>>
When the system is powered, the service user should check the reported value of adjustment grid
voltage in the Service screen with / without a running treatment plan.
<<<
PREREQUISITES: >>>
* The system is powered on and ready to use.
* The user of the system needs to be a service user.
* A treatment plan should be ready to load.
<<<
STEPS: >>>
1. Power on the system.
2. Click Services symbol in the left-hand side of screen.
3. Check the value of the reported grid voltage.
4. Load a treatment plan.
5. Check the state of the system.
6. Check the value of the reported grid voltage.
<<<
EXPECTED_BEHAVIOR: >>>
1. Verify the system is powered on successfully.
2. Verify the services displayed in the middle of screen.
3. Record the reported adjustment grid voltage.
4. Verify the plan is loaded successfully.
5. Verify its state is Ready.
6. Record the reported adjustment grid voltage which is provided by firmware application.
<<<
RELATIONS:
- TYPE: Parent
  VALUE: RQ-H1FWHVPS-12
  ROLE: Verifies

[TEST_CASE]
UID: TC-H1FWHVPS-29
TITLE: Filament current feedback - Test Case
STATEMENT: >>>
When the system is powered, the service user should check the reported value of filament current
in the Service screen with / without a running treatment plan.
<<<
PREREQUISITES: >>>
* The system is powered on and ready to use.
* The user of the system needs to be a service user.
* A treatment plan should be ready to load.
<<<
STEPS: >>>
1. Power on the system.
2. Click Services symbol in the left side of the screen.
3. Look for value of filament current in the service screen.
4. Load a treatment plan.
5. Check the status of the system.
6. Look for value of filament current in the service screen.
<<<
EXPECTED_BEHAVIOR: >>>
1. Verify the system is powered on successfully.
2. Verify the service screen displayed.
3. Record the value and verify the output control signal of the filament current is provided by firmware application.
4. Verify the plan is loaded successfully.
5. Verify the status of the system is ready.
6. Record the value and verify the output control signal of the filament current is provided by firmware application.
<<<
RELATIONS:
- TYPE: Parent
  VALUE: RQ-H1FWHVPS-13
  ROLE: Verifies

[TEST_CASE]
UID: TC-H1FWHVPS-30
TITLE: Emission-current grid regulation - Test Case
STATEMENT: >>>
Verify that the firmware adjusts the grid voltage using cathode-current feedback to maintain
the requested emission current during emission.
<<<
PREREQUISITES: >>>
* The system is powered on and ready to use.
* A treatment plan is ready to load and grid control is enabled.
* A fixture can control cathode-current feedback above and below the requested current.
* The measured cathode current and grid command can be observed.
<<<
STEPS: >>>
1. Load the treatment plan and record the requested emission current.
2. Start emission and observe the measured current and grid command.
3. Use the fixture to produce current below the target and observe the regulation response.
4. Repeat with current above the target.
5. Allow the current to settle after each disturbance and record the result.
<<<
EXPECTED_BEHAVIOR: >>>
1. Verify the requested emission current matches the treatment plan.
2. Verify grid regulation is active during emission.
3. Verify the grid command adjusts in the direction that increases current toward the target.
4. Verify the grid command adjusts in the direction that decreases current toward the target.
5. Verify the measured current returns to and remains within the defined tolerance of the target, with the grid command within configured operating limits.
<<<
RELATIONS:
- TYPE: Parent
  VALUE: RQ-H1FWHVPS-14
  ROLE: Verifies

[TEST_CASE]
UID: TC-H1FWHVPS-31
TITLE: FTDI Bootloader Entry - Test Case
STATEMENT: >>>
A valid FTDI bootloader request shall cause the application firmware to reset into the bootloader.
<<<
PREREQUISITES: >>>
* The system is powered on and running the application firmware.
* A USB FTDI host tool that can transmit the seven-byte bootloader frame is connected to USART3.
* An approved method is available to observe the system reset and confirm that the bootloader is active.
<<<
STEPS: >>>
1. Confirm that the application firmware is running and responding normally.
2. Send the seven-byte `*B00TL\n` frame over the FTDI interface.
3. Observe the reset and interrogate the bootloader with the approved host tool.
<<<
EXPECTED_BEHAVIOR: >>>
1. Verify the application is operational before the request.
2. Verify the application resets after receiving the valid bootloader frame.
3. Verify the bootloader becomes active and accepts the approved host interaction.
<<<
RELATIONS:
- TYPE: Parent
  VALUE: RQ-H1FWHVPS-19
  ROLE: Verifies

[TEST_CASE]
UID: TC-H1FWHVPS-32
TITLE: FTDI Unknown-Command Rejection and Recovery - Test Case
STATEMENT: >>>
The application shall ignore an unrecognized FTDI command and remain able to process a subsequent
valid command.
<<<
PREREQUISITES: >>>
* The system is powered on and running the application firmware.
* A USB FTDI host tool that can transmit and capture binary frames is connected to USART3.
* A valid configuration index and its expected value are available.
<<<
STEPS: >>>
1. Confirm that the application firmware is running and responding normally.
2. Send the unrecognized seven-byte `*B00TX\n` frame over the FTDI interface.
3. Confirm that the application remains operational and that no response is transmitted.
4. Send a valid 11-byte GET frame for the selected configuration index and capture the response.
<<<
EXPECTED_BEHAVIOR: >>>
1. Verify the application is operational before testing.
2. Verify the unrecognized command does not reset the system and produces no response.
3. Verify the subsequent GET request returns the expected configuration value, demonstrating that
   FTDI reception recovered for the next valid command.
<<<
RELATIONS:
- TYPE: Parent
  VALUE: RQ-H1FWHVPS-19
  ROLE: Verifies

[TEST_CASE]
UID: TC-H1FWHVPS-38
TITLE: FTDI Configuration GET and SET Commands - Test Case
STATEMENT: >>>
When the system is powered on, the user can retrieve or update an individual configuration
parameter through the FTDI GET and SET protocol. Binary payload bytes do not end a frame early, and
the receiver remains available after traffic arrives while a complete frame awaits processing.
<<<
PREREQUISITES: >>>
* The system is powered on and ready to use.
* A USB FTDI host tool that can transmit and capture binary frames is connected to the HVPS board.
* A valid configuration index and an approved value whose little-endian float encoding contains a
  `0x0A` payload byte are available.
* An approved FTDI timing harness can delay deferred command processing while UART receive
  interrupts continue.
<<<
STEPS: >>>
1. Power on the system and begin capturing FTDI traffic.
2. Send an 11-byte GET frame containing `*GET..`, configuration category 0 as a little-endian
   16-bit value, the valid index as a little-endian 16-bit value, and a newline terminator.
3. Record the returned value and response bytes.
4. Send a 15-byte SET frame containing `*..SET`, the same category and index fields, the approved
   value containing the `0x0A` payload byte, and a newline terminator.
5. Record the SET response, then repeat the GET request and record its response.
6. Use the timing harness to deliver one additional byte after a complete valid GET frame while
   deferred processing of that frame remains pending. Release processing, wait for it to complete,
   then send and capture another valid GET request.
7. Send separate requests with an unrecognized command header, an unsupported category, a SET index
   outside the configuration table, and an index of 64 or greater.
<<<
EXPECTED_BEHAVIOR: >>>
1. Verify the valid GET returns a 15-byte frame containing `*GET..`, the requested category and
   index, the selected value as a little-endian IEEE-754 32-bit float, and a newline terminator.
2. Verify the `0x0A` payload byte does not terminate the SET frame early. The SET updates the
   selected configuration parameter and returns the corresponding 15-byte `*..SET` confirmation.
3. Verify the repeated GET returns the updated value.
4. Verify the additional byte received while processing is pending is discarded without stalling
   reception, and the final valid GET returns the expected response.
5. Verify each unsupported request is ignored without a response and does not change the selected
   configuration parameter.
<<<
RELATIONS:
- TYPE: Parent
  VALUE: RQ-H1FWHVPS-19
  ROLE: Verifies

[TEST_CASE]
UID: TC-H1FWHVPS-39
TITLE: FTDI Bulk-Read Commands - Test Case
STATEMENT: >>>
When the system is powered on, the user can retrieve every configuration value, setpoint, or
feedback value with the corresponding FTDI bulk-read command.
<<<
PREREQUISITES: >>>
* The system is powered on and ready to use.
* A USB FTDI host tool that can transmit and capture binary frames is connected to the HVPS board.
* The expected 32 configuration values and six setpoints are available by index.
* Stable feedback inputs are applied and the expected five feedback values are independently
  observable.
<<<
STEPS: >>>
1. Power on the system and begin capturing FTDI traffic.
2. Send the seven-byte `*ACFGS\n` request and capture the complete response.
3. Send the seven-byte `*ASPTS\n` request and capture the complete response.
4. Record the five stable feedback values, send the seven-byte `*AFBVS\n` request, and capture the
   complete response.
5. Decode the bytes after each response's six-byte `*` and command header as consecutive
   little-endian IEEE-754 32-bit floats through the final newline.
<<<
EXPECTED_BEHAVIOR: >>>
1. Verify `ACFGS` produces exactly one 135-byte response beginning with `*ACFGS`, followed by all 32
   configuration values in increasing index order, and ending with a newline.
2. Verify `ASPTS` produces exactly one 31-byte response beginning with `*ASPTS`, followed by all six
   setpoints in increasing index order, and ending with a newline.
3. Verify `AFBVS` produces exactly one 27-byte response beginning with `*AFBVS`, followed by all five
   feedback values in increasing index order, and ending with a newline.
4. Verify every decoded value matches the corresponding expected value for its category and index.
<<<
RELATIONS:
- TYPE: Parent
  VALUE: RQ-H1FWHVPS-19
  ROLE: Verifies

[TEST_CASE]
UID: TC-H1FWHVPS-33
TITLE: Filament-current ramping - Test Case
STATEMENT: >>>
Verify that filament current ramps during warmup, warmup completes when current is stable,
and the filament output stops when a persistent feedback mismatch occurs.
<<<
PREREQUISITES: >>>
* The system is powered on and a treatment plan is ready to load.
* A test fixture can control filament-current feedback.
* The requested current, measured current, filament command, and warming status can be observed.
* The configured filament-current limits are available.
<<<
STEPS: >>>
1. Load the treatment plan and observe filament-current ramping during warmup.
2. Hold measured current between the target and 2% above it for 4 seconds.
3. Restart warmup. Once the command reaches the configured minimum, hold measured current
   more than 300 mA below the command for 6 seconds.
4. Request a filament-current target below the configured minimum.
<<<
EXPECTED_BEHAVIOR: >>>
1. Verify the filament command increases gradually during warmup and stays within configured limits.
2. Verify warming remains active until the current has been stable for 4 seconds, then clears.
3. Verify the filament command becomes zero and warming clears after the mismatch persists
   for 6 seconds.
4. Verify the requested target and filament command become zero and warming clears.
<<<
RELATIONS:
- TYPE: Parent
  VALUE: RQ-H1FWHVPS-6
  ROLE: Verifies
- TYPE: Parent
  VALUE: RQ-H1FWHVPS-13
  ROLE: Verifies
- TYPE: Parent
  VALUE: RQ-H1FWHVPS-17
  ROLE: Verifies

[TEST_CASE]
UID: TC-H1FWHVPS-34
TITLE: High voltage setpoint 1 - Test Case
STATEMENT: >>>
When user loads a treatment plan and it is ready for running, make sure the firmware provides and
sets the high voltage setpoint.
<<<
PREREQUISITES: >>>
* The system is powered on and ready to run any treatment plan.
* A treatment plan is ready to load into the system.
<<<
STEPS: >>>
1. Power on the system.
2. Load a 20 second treatment plan.
3. Check the state of the system.
4. Check the value of the reported high voltage.
<<<
EXPECTED_BEHAVIOR: >>>
1. Verify the system is powered on successfully.
2. Verify the plan is loaded successfully.
3. Verify its state is Ready.
4. Record the value and verify it's within 10% of loaded treatment target.
<<<
RELATIONS:
- TYPE: Parent
  VALUE: RQ-H1FWHVPS-2
  ROLE: Verifies

[TEST_CASE]
UID: TC-H1FWHVPS-35
TITLE: External ADC feedback acquisition - Test Case
STATEMENT: >>>
Verify that the firmware reads high-voltage and cathode-current feedback and reports
the correct values in UCSI.
<<<
PREREQUISITES: >>>
* The system is powered on and connected to UCSI with live telemetry available.
* A signal source or HVPS test fixture can provide known feedback inputs.
* Expected high-voltage and cathode-current values and acceptable measurement tolerances
  are defined for the selected inputs.
<<<
STEPS: >>>
1. Apply known high-voltage and cathode-current feedback inputs.
2. Observe and record the corresponding feedback values in UCSI.
3. Change each input separately and verify the corresponding displayed value updates.
4. Repeat for low, middle, and high values within the approved operating range.
<<<
EXPECTED_BEHAVIOR: >>>
1. Verify both feedback values are available in UCSI.
2. Verify the displayed values match the expected values within the defined tolerances.
3. Verify changing either input updates the corresponding feedback value without incorrectly
   changing the other.
4. Verify the displayed values remain within the defined tolerances at all tested inputs.
<<<
RELATIONS:
- TYPE: Parent
  VALUE: RQ-H1FWHVPS-10
  ROLE: Verifies
- TYPE: Parent
  VALUE: RQ-H1FWHVPS-11
  ROLE: Verifies
- TYPE: Parent
  VALUE: RQ-H1FWHVPS-14
  ROLE: Verifies

[TEST_CASE]
UID: TC-H1FWHVPS-37
TITLE: Logging - Test Case
STATEMENT: >>>
Verify formatted, bounded, non-blocking diagnostic logging on FTDI_TX, including
safety-input transition records, severity records, runtime disabling, and transmit-buffer
exhaustion behavior.
<<<
PREREQUISITES: >>>
* The firmware is built with FTDI logging and all four severity levels enabled.
* A serial capture tool is connected to FTDI_TX (USART3) using the configured UART settings.
* A debugger or approved firmware test hook can invoke each severity macro, status reporting, enable or
  disable runtime logging, generate an oversized formatted record, rapidly generate enough records to
  fill the transmit buffer, and inject a recoverable USART3 error.
* A heartbeat output or normal firmware command response is observable while logging is stressed.
* The main-control HV interlock, grid interlock, and beam-control inputs can each be driven
  through debounced rising and falling transitions.
<<<
STEPS: >>>
1. Start serial capture, power the system, and retain the complete startup output.
2. Drive the HV interlock, grid interlock, and beam-control inputs through one debounced
   rising edge and one debounced falling edge each.
3. Emit ERROR, WARN, INFO, and DEBUG records containing known formatted values, then
   request a status record with known `sys_stat` and `sys_io_bits` values.
4. Emit a formatted record whose content exceeds the 256-byte working-buffer capacity.
5. Disable runtime logging, emit a unique marker, re-enable logging, and emit a second
   unique marker.
6. While observing the heartbeat or normal command processing, generate records faster
   than FTDI_TX can transmit until the transmit ring buffer is full; then stop generating
   records and allow it to drain.
7. Inject a recoverable USART3 error and emit another unique marker.
<<<
EXPECTED_BEHAVIOR: >>>
1. Startup output contains the INFO severity marker and `Sensus setup complete`, terminated by CRLF.
2. Each input edge produces exactly one WARN record: `Hv int rose`, `Hv int fell`,
   `Grid int rose`, `Grid int fell`, `Beam ctrl rose`, and `Beam ctrl fell`.
3. The four known records contain the expected `[ERR]`, `[WRN]`, `[INF]`, and `[DBG]`
   markers and correctly formatted values; every complete record is CRLF-terminated. The
   status record is valid newline-delimited JSON containing `runtime_ms` and the expected
   hexadecimal `sys_stat` and `sys_io_bits` values.
4. The oversized record is truncated to no more than 255 transmitted bytes, including its
   CRLF terminator, and logging continues with later records.
5. No disabled-period marker is transmitted; the marker emitted after re-enabling logging
   is transmitted.
6. The heartbeat or command responses continue without a logging-induced stall. When
   capacity is exhausted, excess bytes are dropped rather than blocking application
   processing, and bytes accepted before exhaustion drain in order through
   transmit-complete interrupts.
7. UART error flags clear and the post-error marker is transmitted.
<<<
RELATIONS:
- TYPE: Parent
  VALUE: RQ-H1FWHVPS-18
  ROLE: Verifies

[TEST_CASE]
UID: TC-H1FWHVPS-40
TITLE: Firmware version reporting - Test Case
STATEMENT: >>>
Verify that UCSI displays the correct HVPS firmware version and live telemetry continues updating.
<<<
PREREQUISITES: >>>
* The system is powered on and connected to UCSI.
* The expected HVPS firmware version is known.
<<<
STEPS: >>>
1. Open UCSI and wait for firmware information to appear.
2. Record the value displayed under HVPS firmware.
3. Compare it with the expected firmware version.
4. Observe live telemetry after the version is displayed.
<<<
EXPECTED_BEHAVIOR: >>>
1. Verify the HVPS firmware version is displayed.
2. Verify the displayed version matches the expected version.
3. Verify live telemetry continues updating without interruption.
<<<
RELATIONS:
- TYPE: Parent
  VALUE: RQ-H1FWHVPS-20
  ROLE: Verifies

[[/SECTION]]

[DOCUMENT]
TITLE: GBSK HVPS Interface Application FW Software Requirements Specification
UID: DHF-GBSK-0019
METADATA:
  COMPONENT: hvps-interface/main

[GRAMMAR]
IMPORT_FROM_FILE: @grammar

[[SECTION]]
TITLE: Purpose

[TEXT]
STATEMENT: >>>
The purpose of this document is to provide Software Requirements Specifications for the GBSK
HVPS Interface Application Firmware (FW).
<<<

[[/SECTION]]

[[SECTION]]
TITLE: Scope

[TEXT]
STATEMENT: >>>
This document describes all requirements of the GBSK HVPS Interface Application FW. The
information in this document has been derived from the VoxelRay GBSK Product Requirements
Specification.

\*The term Software applies to both Software and Firmware systems.
<<<

[[/SECTION]]

[[SECTION]]
TITLE: Abbreviations and Definitions

[TEXT]
STATEMENT: >>>
FW
  Firmware

HVPS
  High Voltage Power Supply

LED
  Light Emitting Diode

MCU
  Microcontroller Unit

PID
  Proportional Integral Derivative controller

PRS
  Product Requirements Specification

SDP
  Software Development Plan

SRS
  Software Requirements Specification

SW
  Software
<<<

[[/SECTION]]

[[SECTION]]
TITLE: Overview

[TEXT]
STATEMENT: >>>
The HVPS interface application firmware is used to control and receive feedback from HVPS.

The HVPS interface application firmware reports data back to and receives commands from the main
control application firmware. The HVPS interface application firmware contains routines to ramp up
the filament current, as well as the high voltage. It contains a feedback-control loop for
regulating the emission output to a given setpoint.

The HVPS interface application firmware runs on the MCU of the HVPS interface board.
<<<

[[/SECTION]]

[[SECTION]]
TITLE: References

[TEXT]
STATEMENT: >>>
GBSK SDP: DHF-GBSK-0001 Rev. 1

GBSK SVP: DHF-GBSK-0003 Rev. 1

GBSK FW Architecture Description: DHF-GBSK-0031 Rev. 1

GBSK HVPS Interface Application FW SDD: DHF-GBSK-0096 Rev. 1
<<<

[[/SECTION]]

[[SECTION]]
PREFIX: RQ-H1FWHVPS-
TITLE: Requirements

[REQUIREMENT]
UID: RQ-H1FWHVPS-1
TYPE: Safety
TITLE: Grid control clock
STATEMENT: >>>
The firmware shall be able to generate an output for a grid control clock at a frequency between 1
kHz and 20 kHz
<<<

[REQUIREMENT]
UID: RQ-H1FWHVPS-2
TYPE: Functional
TITLE: Runtime counter
STATEMENT: >>>
The firmware shall be able to maintain a runtime counter which updates every 1 ms
<<<

[REQUIREMENT]
UID: RQ-H1FWHVPS-4
TYPE: Functional
TITLE: Main control reporting
STATEMENT: >>>
The firmware shall periodically report values to the main control board at a rate greater than 1 Hz
<<<

[REQUIREMENT]
UID: RQ-H1FWHVPS-5
TYPE: Functional
TITLE: HVPS digital status signals
STATEMENT: >>>
The firmware shall read and report each HVPS digital status input according to its asserted
state. Reported fault statuses shall remain latched until explicitly cleared.
<<<

[REQUIREMENT]
UID: RQ-H1FWHVPS-6
TYPE: Functional
TITLE: Filament current setpoint
STATEMENT: >>>
The firmware shall be able to accept a command from the main control board to set a target filament
current setpoint
<<<

[REQUIREMENT]
UID: RQ-H1FWHVPS-7
TYPE: Functional
TITLE: Dynamic grid setpoint
STATEMENT: >>>
The firmware shall be able to accept a command from the main control board to set a target dynamic
grid setpoint
<<<

[REQUIREMENT]
UID: RQ-H1FWHVPS-8
TYPE: Functional
TITLE: High voltage setpoint
STATEMENT: >>>
The firmware shall be able to accept a command from the main control board to set a target high
voltage setpoint
<<<

[REQUIREMENT]
UID: RQ-H1FWHVPS-9
TYPE: Functional
TITLE: Cathode current limiter setpoint
STATEMENT: >>>
The firmware shall be able to accept a command from the main control board to set a cathode current
limiter
<<<

[REQUIREMENT]
UID: RQ-H1FWHVPS-10
TYPE: Functional
TITLE: Cathode current feedback
STATEMENT: >>>
The firmware shall be able to read and report the feedback signal for the cathode current
<<<

[REQUIREMENT]
UID: RQ-H1FWHVPS-11
TYPE: Functional
TITLE: High voltage feedback
STATEMENT: >>>
The firmware shall be able to read and report the feedback signal for the high voltage
<<<

[REQUIREMENT]
UID: RQ-H1FWHVPS-12
TYPE: Functional
TITLE: Adjustment grid voltage feedback
STATEMENT: >>>
The firmware shall be able to read and report the feedback signal for the adjustment grid voltage
<<<

[REQUIREMENT]
UID: RQ-H1FWHVPS-13
TYPE: Functional
TITLE: Filament current feedback
STATEMENT: >>>
The firmware shall be able to read and report the feedback signal for the filament current
<<<

[REQUIREMENT]
UID: RQ-H1FWHVPS-14
TYPE: Functional
TITLE: Control loop
STATEMENT: >>>
The firmware shall use high-voltage and cathode-current feedback to adjust output commands
during X-ray emission and stabilize emission output within the configured operating limits.
<<<

[REQUIREMENT]
UID: RQ-H1FWHVPS-17
TYPE: Functional
TITLE: Filament current ramp up
STATEMENT: >>>
The firmware shall ramp filament current at a controlled rate, determine when the requested
target is stable, and terminate the ramp when the commanded and measured currents remain
unacceptably different.
<<<

[REQUIREMENT]
UID: RQ-H1FWHVPS-18
TYPE: Functional
TITLE: Logging
STATEMENT: >>>
The firmware shall provide diagnostic logging without blocking application processing.
<<<

[REQUIREMENT]
UID: RQ-H1FWHVPS-19
TYPE: Functional
TITLE: FTDI Host Interface
STATEMENT: >>>
The firmware shall provide an FTDI UART interface through which a connected host can read device
parameters, update supported configuration parameters, and request bootloader entry.
<<<

[REQUIREMENT]
UID: RQ-H1FWHVPS-20
TYPE: Functional
TITLE: Firmware version reporting
STATEMENT: >>>
The firmware shall report its release version when requested by the main control board.
<<<

[[/SECTION]]

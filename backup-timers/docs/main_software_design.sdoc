[DOCUMENT]
TITLE: GBSK Backup Timer FW Software Design Document
UID: DHF-GBSK-0087
METADATA:
  COMPONENT: backup-timers

[GRAMMAR]
IMPORT_FROM_FILE: @grammar

[[SECTION]]
TITLE: Purpose

[TEXT]
STATEMENT: >>>
The purpose of this document is to outline the design specifications of the GBSK Backup Timer
Firmware.
<<<

[[/SECTION]]

[[SECTION]]
TITLE: Scope

[TEXT]
STATEMENT: >>>
This document describes the design modules and sub-modules of the GBSK Backup Timer Firmware. The information in this document is derived from the Backup Timer FW SRS, referenced in this document.

\*The term Software applies to both Software and Firmware components.
<<<

[[/SECTION]]

[[SECTION]]
TITLE: Abbreviations and Definitions

[TEXT]
STATEMENT: >>>
FW
  Firmware

MCU
  Microcontroller Unit

PRS
  Product Requirements Specification

SDP
  Software Development Plan

SRS
  Software Requirements Specification

SW
  Software
<<<

[[/SECTION]]

[[SECTION]]
TITLE: Overview

[TEXT]
STATEMENT: >>>
The Backup Timer firmware is used to interface with the main control firmware and count the registered
course of time once prompted. If the set period has elapsed, the timer firmware will trigger the timer MCU
to terminate the X-Ray emission.

The Backup Timer firmware runs on the Timer MCUs located on the main control board.
<<<

[[/SECTION]]

[[SECTION]]
TITLE: References

[TEXT]
STATEMENT: >>>
DHF-GBSK-0001, Rev. 1: GBSK Software Development Plan (SDP)

DHF-GBSK-0003, Rev. 1: GBSK Software Verification Plan (SVP)

DHF-GBSK-0017, Rev. 1: GBSK Backup Timer Software Requirements Specification (SRS)

DHF-GBSK-0031, Rev. 1: GBSK Firmware Architecture Description
<<<

[[/SECTION]]

[[SECTION]]
TITLE: Architecture Overview

[[SECTION]]
TITLE: High Level System Architecture

[TEXT]
STATEMENT: >>>
.. raw:: html

    <pre class="mermaid">
    flowchart LR

    FW["Main Control Firmware"]

    subgraph ET["External Timer"]
        direction TB
        I2C["I2C Interface"]
    end

    DebugLED["Debug LED"]

    FW <--> I2C
    ET --> DebugLED
    </pre>
<<<

[[/SECTION]]

[[SECTION]]
TITLE: Main Modules

[TEXT]
STATEMENT: >>>
**External Timer** a.k.a. Backup Timer. This is a redundant timer that is started in conjunction with the
Main Control's internal timer and a paired external timer. It reports its time, state, and whether there are
any faults to the main control firmware.

**Main Control Firmware** Sends start, stop, reset commands to the Timer.

**Debug LED** discrete LED that provides visual feedback to the user based on the Timer's status.
<<<

[[/SECTION]]

[[SECTION]]
PREFIX: SW-H1FWT-
TITLE: Design Items

[DESIGN_ITEM]
UID: SW-H1FWT-28
TITLE: Communication Interface
STATEMENT: >>>
The timer firmware communicates with the main control application firmware. The timer firmware in
response reports the current remaining or elapsed time. This communication takes place using an
I2C bus. The firmware utilizes the timer MCU's built in I2C peripheral hardware instead of manually
'bit-banging' a set of general IO. The firmware sets up the timer MCU as an I2C slave device to the
main control MCU's master device.

At the board level of hardware, there are two timer MCUs which share a single I2C bus with the
main control MCU that acts as the master. Due to this, the two timer MCUs need to have different
I2C addresses. Instead of building and maintaining two versions of timer firmware, the two timer
MCUs instead have either a pull-up or pull-down resistor on one of their input pins. This pin value is
read at the start of firmware execution and is used to determine which slave address is used for the
specific MCU that the firmware is running on.

The firmware enables the I2C peripheral's data received interrupt, which allows an interrupt to be
processed whenever a data byte is received from the I2C master. Once a complete data packet is
received, per the application-level communication protocol, a flag is set so that synchronous packet
processing may be performed on the data.
<<<
RELATIONS:
- TYPE: Parent
  VALUE: RQ-H1FWT-5
  ROLE: Refines
- TYPE: Parent
  VALUE: RQ-H1FWT-6
  ROLE: Refines
- TYPE: Parent
  VALUE: RQ-H1FWT-14
  ROLE: Refines

[DESIGN_ITEM]
UID: SW-H1FWT-29
TITLE: Time Keeping
STATEMENT: >>>
To perform the time counting, the firmware utilizes one of the MCU's internal timer hardware
peripherals. The hardware timer peripheral was selected as it can run independently from the CPU
instructions and keep accurate time, while not having to deal with other processing such as
handling messaging to and from the main control MCU. One downside to this is that the time value
must be manually copied and updated every time it needs to be sent to the main controller. In
firmware this is done every time the main controller requests a new value via the I2C
communication. The tradeoff is worth it, as the small amount of time spent copying is much less
than the extra processing timer required if the MCU attempted to constantly 'manually' update a
value at the same rate.

The timer peripheral is configured to utilize an external 32.768 kHz crystal as a clock source for
increased accuracy. No pre-scaler values are used, and so the count rate of the timer is 32.768
kHz. The 'raw' time value is represented by 'ticks', where 32,768 'ticks' represent one second of
time passage. The firmware utilizes the desired operational timing value in 'ticks' as the value for
triggering the hardware peripheral's comparison interrupt. The hardware peripheral utilizes 32-bit
registers for counting and for comparison, so the maximum timer runtime is 36 hours.

The method by which the emission timeout period is determined is by using the peripheral
hardware's compare functionality. After being reset and then enabled, the timer peripheral will start
counting up from 0. By setting the desired timeout tick period in the peripheral's compare register,
an interrupt service routine is triggered once the count value of the timer's value register matches
the stored compare register value. The firmware can then stop emission output within the interrupt
processing function that is called.
<<<
RELATIONS:
- TYPE: Parent
  VALUE: RQ-H1FWT-1
  ROLE: Refines
- TYPE: Parent
  VALUE: RQ-H1FWT-2
  ROLE: Refines
- TYPE: Parent
  VALUE: RQ-H1FWT-3
  ROLE: Refines
- TYPE: Parent
  VALUE: RQ-H1FWT-4
  ROLE: Refines
- TYPE: Parent
  VALUE: RQ-H1FWT-10
  ROLE: Refines
- TYPE: Parent
  VALUE: RQ-H1FWT-11
  ROLE: Refines
- TYPE: Parent
  VALUE: RQ-H1FWT-12
  ROLE: Refines
- TYPE: Parent
  VALUE: RQ-H1FWT-13
  ROLE: Refines

[DESIGN_ITEM]
UID: SW-H1FWT-30
TITLE: Input Signals
STATEMENT: >>>
The firmware enables an IO input interrupt for determining when to start the timer count. This
interrupt is configured to trip on the signal rising edge.

The firmware reads an IO input which is either pulled up or down to determine the I2C slave
address to be used.

The firmware utilizes external crystal input as the clock source for its peripheral hardware so that
accurate timing counts may be produced.
<<<
RELATIONS:
- TYPE: Parent
  VALUE: RQ-H1FWT-5
  ROLE: Refines
- TYPE: Parent
  VALUE: RQ-H1FWT-11
  ROLE: Refines
- TYPE: Parent
  VALUE: RQ-H1FWT-14
  ROLE: Refines

[DESIGN_ITEM]
UID: SW-H1FWT-31
TITLE: Output Signals
STATEMENT: >>>
The firmware has one LED output control signal for debugging.

The firmware has one interlock fault output signal which can trigger to stop emission of the system.
<<<
RELATIONS:
- TYPE: Parent
  VALUE: RQ-H1FWT-9
  ROLE: Refines

[DESIGN_ITEM]
UID: SW-H1FWT-32
TITLE: Communication Protocol
STATEMENT: >>>
The communication data from the main control firmware are commands which are timer related
tasks. These commands are setting the target time, pausing the timer counting and resetting the
timer (including the interlock IO used to terminate emissions), as well as a report time request.
There is no start command, as start is performed via hardware IO. This is due to the two timer
MCUs sharing a single serial communication bus. To ensure that the timer counts are as
synchronized as possible, the trigger to start is instead done via a digital signal rather than
sequential serial commands. This signal only starts with the count of the timers and cannot stop
them.

The communication data to the main control firmware reports the time value being counted, as well
as the state of the timer.

Both received and sent messages use a simple checksum value to check the validity of the
message payloads
<<<
RELATIONS:
- TYPE: Parent
  VALUE: RQ-H1FWT-14
  ROLE: Refines

[DESIGN_ITEM]
UID: SW-H1FWT-33
TITLE: Manufacturer Hardware Abstraction
STATEMENT: >>>
The firmware integrates source code provided by the manufacturer of the microcontroller unit to
interface with various peripherals of the microcontroller. These include functions to interface with
the following peripherals of the microcontroller:

- I2C serial port
- GPIO
- Timer counter
<<<
RELATIONS:
- TYPE: Parent
  VALUE: RQ-H1FWT-1
  ROLE: Refines
- TYPE: Parent
  VALUE: RQ-H1FWT-3
  ROLE: Refines
- TYPE: Parent
  VALUE: RQ-H1FWT-4
  ROLE: Refines
- TYPE: Parent
  VALUE: RQ-H1FWT-6
  ROLE: Refines
- TYPE: Parent
  VALUE: RQ-H1FWT-9
  ROLE: Refines
- TYPE: Parent
  VALUE: RQ-H1FWT-12
  ROLE: Refines
- TYPE: Parent
  VALUE: RQ-H1FWT-13
  ROLE: Refines
- TYPE: Parent
  VALUE: RQ-H1FWT-14
  ROLE: Refines

[DESIGN_ITEM]
UID: SW-H1FWT-58
TITLE: I2C Address
STATEMENT: >>>
At the board level of hardware, there are two timer MCUs which share a single I2C bus with the
main control MCU that acts as the master. Due to this, the two timer MCUs need to have different
I2C addresses. Instead of building and maintaining two versions of timer firmware, the two timer
MCUs instead have either a pull-up or pull-down resistor on one of their input pins. This pin value is
read at the start of firmware execution and is used to determine which slave address is used for the
specific MCU that the firmware is running on.
<<<
RELATIONS:
- TYPE: Parent
  VALUE: RQ-H1FWT-5
  ROLE: Refines
- TYPE: Parent
  VALUE: RQ-H1FWT-6
  ROLE: Refines
- TYPE: Parent
  VALUE: SW-H1FWT-28
  ROLE: Refines

[[/SECTION]]

[[/SECTION]]

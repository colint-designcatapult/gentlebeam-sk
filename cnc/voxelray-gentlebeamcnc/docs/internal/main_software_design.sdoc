[DOCUMENT]
TITLE: GBSK Software Design Document for Internal GUI
UID: DHF-GBSK-0033
METADATA:
  COMPONENT: heracles-internal-gui

[GRAMMAR]
IMPORT_FROM_FILE: @grammar

[[SECTION]]
TITLE: Purpose

[TEXT]
STATEMENT: >>>
The purpose of this document is to outline the design specifications of the GBSK Internal GUI Software.
<<<

[[/SECTION]]

[[SECTION]]
TITLE: Scope

[TEXT]
STATEMENT: >>>
This document describes the design modules and sub-modules of the GBSK Internal GUI Software.

The information in this document is derived from the Internal GUI SRS, referenced in this document.

\*The term Software applies to both Software and Firmware components.
<<<

[[/SECTION]]

[[SECTION]]
TITLE: Abbreviations and Definitions

[TEXT]
STATEMENT: >>>
FW
Firmware

MCU
Microcontroller Unit

PRS
Product Requirements Specification

SDP
Software Development Plan

SRS
Software Requirements Specification

SVP
Software Verification Plan

SW
Software
<<<

[[/SECTION]]

[[SECTION]]
TITLE: Overview

[TEXT]
STATEMENT: >>>
The Internal GUI SW provides a means for the user to maintain demographic patient data, including treatment plans. It communicates with the database and flange camera stream.

The internal GUI software runs on an industrial PC located at the base of the system
<<<

[[/SECTION]]

[[SECTION]]
TITLE: References

[TEXT]
STATEMENT: >>>
Document ID / Reference Number: DHF-GBSK-0001, Rev. 1
Document TITLE: GBSK Software Development Plan (SDP)

Document ID / Reference Number: DHF-GBSK-0003, Rev. 1
Document TITLE: GBSK Software Verification Plan (SVP)

Document ID / Reference Number: DHF-GBSK-0005, Rev. 3
Document TITLE: GBSK Internal GUI Software Requirements Specification (SRS)

Document ID / Reference Number: DHF-GBSK-0004, Rev. 1
Document TITLE: GBSK Software Architecture Description
<<<

[[/SECTION]]

[[SECTION]]
TITLE: Architecture Overview

[TEXT]
STATEMENT: >>>
High Level System Architecture

Main Modules

The design of the application is based on the MVVM pattern. There are three core components in the MVVM pattern: the model, the view, and the view model. Each serves a distinct purpose. The diagram below shows the relationships between the three components.

The MVVN design pattern is implemented in the application as follows: the 4 th layer is the gRPC wrapper for communication with database services.
<<<

[[/SECTION]]

[[SECTION]]
PREFIX: SW-H10SG-
TITLE: Design Items

[DESIGN_ITEM]
UID: SW-H10SG-11
TITLE: Data management API
STATEMENT: >>>
In embedded database mode, the indoor application hosts a local gRPC database API backed by an encrypted SQLite database. The existing unary API operations store and retrieve data, and streaming subscriptions deliver change notifications. The listener can serve other gRPC clients; database persistence does not require a remote or centralized database service. Existing non-embedded configurations retain their configured database service.

The list of API functions is defined in the following protocol document:

GBSK DB API
<<<
RELATIONS:
- TYPE: Parent
  VALUE: RQ-H10SG-55
  ROLE: Refines

[DESIGN_ITEM]
UID: SW-H10SG-12
TITLE: Patients' Data Management
STATEMENT: >>>
In embedded database mode, the indoor application stores and manages patient information, treatment plans, and treatment history in its local relational repository. SQLCipher protects the whole database, including all patient and non-patient tables, rather than encrypting only patient demographic fields.

The data shall be managed in a relational database, which shall support hierarchical organization based on user flow.

The data shall be stored in the form of JSON-serialized Protocol Buffers based on the communication protocol.
Each Protocol Buffers structure shall have a dedicated database table with the following fields:

- ``id``: integer primary key with AUTOINCREMENT, retained in the serialized entity.
- ``parent_id``: non-null integer, present for child-entity tables to retain the parent-child hierarchy; not present in every table.
- ``data``: non-null TEXT containing the serialized Protocol Buffers JSON.
<<<
RELATIONS:
- TYPE: Parent
  VALUE: RQ-H10SG-55
  ROLE: Refines
- TYPE: Parent
  VALUE: RQ-H10SG-377
  ROLE: Refines

[DESIGN_ITEM]
UID: SW-H10SG-13
TITLE: High Level System Architecture
STATEMENT: >>>
Approvals Calibration - Heater current configuration.

The application is comprised of two key components: GBSK Device Control console (Indoor application) and Treatment Control console (Outdoor application).

The GBSK Device Control console is integrated within the GBSK device. This application addresses functionalities related to patients, demographic data management, clinical data management, treatment data management, user access, clinical workflows, and system setup and services.

The Treatment Control application must be located in a console outside the treatment room. This is to provide the operator with a safe work environment. It should allow healthcare professionals e.g., radiation therapists (RTT), and physicians to activate the radiation emission for the patient's treatment and to provide tools for physicists to program the system's calibration values.
<<<
RELATIONS:
- TYPE: Parent
  VALUE: RQ-H10SG-54
  ROLE: Refines

[DESIGN_ITEM]
UID: SW-H10SG-99
TITLE: Collimator fields name mapping to DB, UI and GCB
STATEMENT: >>>
61 Head collimator Patients - Plan View - Load For Treatment - Cancelation

+------------------------+-----------------+
| Enum Name              | FW: GCB /UI     |
+========================+=================+
| FIELD_NAME_UNSPECIFIED | N/A             |
+------------------------+-----------------+
| FIELD_NAME_PLUS_4L2    | FW: +4L2 UI: 1  |
+------------------------+-----------------+
| FIELD_NAME_PLUS_4L1    | FW: +4L1 UI: 2  |
+------------------------+-----------------+
| FIELD_NAME_PLUS_4C     | FW: +4C UI: 3   |
+------------------------+-----------------+
| FIELD_NAME_PLUS_4R1    | FW: +4R1 UI: 4  |
+------------------------+-----------------+
| FIELD_NAME_PLUS_4R2    | FW: +4R2 UI: 5  |
+------------------------+-----------------+
| FIELD_NAME_PLUS_3L3    | FW: +3L3 UI: 6  |
+------------------------+-----------------+
| FIELD_NAME_PLUS_3L2    | FW: +3L2 UI: 7  |
+------------------------+-----------------+
| FIELD_NAME_PLUS_3L1    | FW: +3L1 UI: 8  |
+------------------------+-----------------+
| FIELD_NAME_PLUS_3R1    | FW: +3R1 UI: 9  |
+------------------------+-----------------+
| FIELD_NAME_PLUS_3R2    | FW: +3R2 UI: 10 |
+------------------------+-----------------+
| FIELD_NAME_PLUS_3R3    | FW: +3R3 UI: 11 |
+------------------------+-----------------+
| FIELD_NAME_PLUS_2L3    | FW: +2L3 UI: 12 |
+------------------------+-----------------+
| FIELD_NAME_PLUS_2L2    | FW: +2L2 UI: 13 |
+------------------------+-----------------+

+----------------------+-----------------+
| FIELD_NAME_PLUS_2L1  | FW: +2L1 UI: 14 |
+======================+=================+
| FIELD_NAME_PLUS_2C   | FW: +2C UI: 15  |
+----------------------+-----------------+
| FIELD_NAME_PLUS_2R1  | FW: +2R1 UI: 16 |
+----------------------+-----------------+
| FIELD_NAME_PLUS_2R2  | FW: +2R2 UI: 17 |
+----------------------+-----------------+
| FIELD_NAME_PLUS_2R3  | FW: +2R3 UI: 18 |
+----------------------+-----------------+
| FIELD_NAME_PLUS_1L4  | FW: +1L4 UI: 19 |
+----------------------+-----------------+
| FIELD_NAME_PLUS_1L3  | FW: +1L3 UI: 20 |
+----------------------+-----------------+
| FIELD_NAME_PLUS_1L2  | FW: +1L2 UI: 21 |
+----------------------+-----------------+
| FIELD_NAME_PLUS_1L1  | FW: +1L1 UI: 22 |
+----------------------+-----------------+
| FIELD_NAME_PLUS_1R1  | FW: +1R1 UI: 23 |
+----------------------+-----------------+
| FIELD_NAME_PLUS_1R2  | FW: +1R2 UI: 24 |
+----------------------+-----------------+
| FIELD_NAME_PLUS_1R3  | FW: +1R3 UI: 25 |
+----------------------+-----------------+
| FIELD_NAME_PLUS_1R4  | FW: +1R4 UI: 26 |
+----------------------+-----------------+
| FIELD_NAME_PLUS_0L4  | FW: +0L4 UI: 27 |
+----------------------+-----------------+
| FIELD_NAME_PLUS_0L3  | FW: +0L3 UI: 28 |
+----------------------+-----------------+
| FIELD_NAME_PLUS_0L2  | FW: +0L2 UI: 29 |
+----------------------+-----------------+
| FIELD_NAME_PLUS_0L1  | FW: +0L1 UI: 30 |
+----------------------+-----------------+
| FIELD_NAME_PLUS_C    | FW: C UI: 31    |
+----------------------+-----------------+
| FIELD_NAME_PLUS_0R1  | FW: +0R1 UI: 32 |
+----------------------+-----------------+
| FIELD_NAME_PLUS_0R2  | FW: +0R2 UI: 33 |
+----------------------+-----------------+
| FIELD_NAME_PLUS_0R3  | FW: +0R3 UI: 34 |
+----------------------+-----------------+
| FIELD_NAME_PLUS_0R4  | FW: +0R4 UI: 35 |
+----------------------+-----------------+
| FIELD_NAME_MINUS_1L4 | FW: -1L4 UI: 36 |
+----------------------+-----------------+

+----------------------+-----------------+
| FIELD_NAME_MINUS_1L3 | FW: -1L3 UI: 37 |
+======================+=================+
| FIELD_NAME_MINUS_1L2 | FW: -1L2 UI: 38 |
+----------------------+-----------------+
| FIELD_NAME_MINUS_1L1 | FW: -1L1 UI: 39 |
+----------------------+-----------------+
| FIELD_NAME_MINUS_1R1 | FW: -1R1 UI: 40 |
+----------------------+-----------------+
| FIELD_NAME_MINUS_1R2 | FW: -1R2 UI: 41 |
+----------------------+-----------------+
| FIELD_NAME_MINUS_1R3 | FW: -1R3 UI: 42 |
+----------------------+-----------------+
| FIELD_NAME_MINUS_1R4 | FW: -1R4 UI: 43 |
+----------------------+-----------------+
| FIELD_NAME_MINUS_2L3 | FW: -2L3 UI: 44 |
+----------------------+-----------------+
| FIELD_NAME_MINUS_2L2 | FW: -2L2 UI: 45 |
+----------------------+-----------------+
| FIELD_NAME_MINUS_2L1 | FW: -2L1 UI: 46 |
+----------------------+-----------------+
| FIELD_NAME_MINUS_2C  | FW: -2C UI: 47  |
+----------------------+-----------------+
| FIELD_NAME_MINUS_2R1 | FW: -2R1 UI: 48 |
+----------------------+-----------------+
| FIELD_NAME_MINUS_2R2 | FW: -2R2 UI: 49 |
+----------------------+-----------------+
| FIELD_NAME_MINUS_2R3 | FW: -2R3 UI: 50 |
+----------------------+-----------------+
| FIELD_NAME_MINUS_3L3 | FW: -3L3 UI: 51 |
+----------------------+-----------------+
| FIELD_NAME_MINUS_3L2 | FW: -3L2 UI: 52 |
+----------------------+-----------------+
| FIELD_NAME_MINUS_3L1 | FW: -3L1 UI: 53 |
+----------------------+-----------------+
| FIELD_NAME_MINUS_3R1 | FW: -3R1 UI: 54 |
+----------------------+-----------------+
| FIELD_NAME_MINUS_3R2 | FW: -3R2 UI: 55 |
+----------------------+-----------------+
| FIELD_NAME_MINUS_3R3 | FW: -3R3 UI: 56 |
+----------------------+-----------------+
| FIELD_NAME_MINUS_4L2 | FW: -4L2 UI: 57 |
+----------------------+-----------------+
| FIELD_NAME_MINUS_4L1 | FW: -4L1 UI: 58 |
+----------------------+-----------------+
| FIELD_NAME_MINUS_4C  | FW: -4C UI: 59  |
+----------------------+-----------------+

+----------------------+-----------------+
| FIELD_NAME_MINUS_4R1 | FW: -4R1 UI: 60 |
+======================+=================+
| FIELD_NAME_MINUS_4R2 | FW: -4R2 UI: 61 |
+----------------------+-----------------+

13 Cells Central Large collimator

+------------------------+-----------------+
| Enum Name              | FW: GCB /UI     |
+========================+=================+
| FIELD_NAME_UNSPECIFIED | N/A             |
+------------------------+-----------------+
| FIELD_NAME_PLUS_2L1    | FW: +2L1 UI: 1  |
+------------------------+-----------------+
| FIELD_NAME_PLUS_2C     | FW: +2C UI: 2   |
+------------------------+-----------------+
| FIELD_NAME_PLUS_2R1    | FW: +2R1 UI: 3  |
+------------------------+-----------------+
| FIELD_NAME_PLUS_1L2    | FW: +1L2 UI: 4  |
+------------------------+-----------------+
| FIELD_NAME_PLUS_1R2    | FW: +1R2 UI: 5  |
+------------------------+-----------------+
| FIELD_NAME_PLUS_0L2    | FW: +0L2 UI: 6  |
+------------------------+-----------------+
| FIELD_NAME_PLUS_C      | FW: C UI: 7     |
+------------------------+-----------------+
| FIELD_NAME_PLUS_0R2    | FW: +0R2 UI: 8  |
+------------------------+-----------------+
| FIELD_NAME_MINUS_1L2   | FW: -1L2 UI: 9  |
+------------------------+-----------------+
| FIELD_NAME_MINUS_1R2   | FW: -1R2 UI: 10 |
+------------------------+-----------------+
| FIELD_NAME_MINUS_2L1   | FW: -2L1 UI: 11 |
+------------------------+-----------------+
| FIELD_NAME_MINUS_2C    | FW: -2C UI: 12  |
+------------------------+-----------------+
| FIELD_NAME_MINUS_2R1   | FW: -2R1 UI: 13 |
+------------------------+-----------------+
<<<
RELATIONS:
- TYPE: Parent
  VALUE: RQ-H10SG-81
  ROLE: Refines

[DESIGN_ITEM]
UID: SW-H10SG-100
TITLE: System Data management
STATEMENT: >>>
In embedded database mode, calibration data, system settings, QC history, and warmup history are stored in the same encrypted local relational database as the patient and treatment records. The existing Protocol Buffers JSON repository representation is retained. SQLCipher provides whole-database encryption and cryptographic page-integrity protection for these system records as well as clinical data.

<<<
RELATIONS:
- TYPE: Parent
  VALUE: RQ-H10SG-126
  ROLE: Refines
- TYPE: Parent
  VALUE: RQ-H10SG-55
  ROLE: Refines
- TYPE: Parent
  VALUE: RQ-H10SG-789
  ROLE: Refines

[DESIGN_ITEM]
UID: SW-H10SG-333
TITLE: Automatically Identify connected collimator type and configuration
STATEMENT: >>>
The Identification of the connected Collimator will be done according to the following sequence diagram:

1. The C&C app queries the connected collimator (chip) for its ID (64-bit ID).

1. The C&C queries DB Service (Moses) for the collimator data for this ID. The return value includes a foreign key for the collimator\_configuration.

2. The C&C queries DB Service for the collimator's configuration, which returns the Type, Energy, and SSD of the connected collimator.
<<<
RELATIONS:
- TYPE: Parent
  VALUE: RQ-H10SG-332
  ROLE: Refines

[DESIGN_ITEM]
UID: SW-H10SG-378
TITLE: Patient - Plan View - Auto-calculate the ICDCode - ICD Code table
STATEMENT: >>>
ICD Code will be generated based on the lesion location (Field Location) and the Pathology as set by the operator:

The calculation will use the following table:

+------------------------------------------------------------------------------+-----------+--------------------------------------------------------+----------------------------------------+-----------------------------+---------------------+
|                                                                              | ICDforBCC | ICDforSCC                                              | ICDforSCC-15                           | ICDforBasosquam             | ICD for Keloid      |
+==============================================================================+===========+========================================================+========================================+=============================+=====================+
| Location                                                                     |           | Basal Cell Carcinoma (Bcc)Squamous Cell Carcinoma(ScC) | Squamous CellCarcinoma-in Situ(SCC-IS) | Basosquamous Cell Carcinoma | Keloid L91.0, L73.0 |
+------------------------------------------------------------------------------+-----------+--------------------------------------------------------+----------------------------------------+-----------------------------+---------------------+
| Breast                                                                       | C44.511   | C44.521                                                | D04.5                                  | C44.591                     |                     |
+------------------------------------------------------------------------------+-----------+--------------------------------------------------------+----------------------------------------+-----------------------------+---------------------+
| Ear (Left)                                                                   | C44.219   | C44.229                                                | D04.22                                 | C44.299                     |                     |
+------------------------------------------------------------------------------+-----------+--------------------------------------------------------+----------------------------------------+-----------------------------+---------------------+
| Ear (Right)                                                                  | C44.212   | C44.222                                                | D04.21                                 | C44.292                     |                     |
+------------------------------------------------------------------------------+-----------+--------------------------------------------------------+----------------------------------------+-----------------------------+---------------------+
| Face&Other Parts of Face [Ex. Cheek,Chin, Forehead,Jaw,Pre-Auricular,Zygoma) | C44.319   | C44.329                                                | D04.39                                 | C44.399                     |                     |
+------------------------------------------------------------------------------+-----------+--------------------------------------------------------+----------------------------------------+-----------------------------+---------------------+
| Lip                                                                          | C44.01    | C44.02                                                 | D04.0                                  | C44.09                      |                     |
+------------------------------------------------------------------------------+-----------+--------------------------------------------------------+----------------------------------------+-----------------------------+---------------------+
| Neck                                                                         | C44.41    | C44.42                                                 | D04.4                                  | C44.49                      |                     |
+------------------------------------------------------------------------------+-----------+--------------------------------------------------------+----------------------------------------+-----------------------------+---------------------+
| Nose (Ex. Ala, Bridge, Tip, Root)                                            | C44.311   | C44.321                                                | D04.39                                 | C44.391                     |                     |
+------------------------------------------------------------------------------+-----------+--------------------------------------------------------+----------------------------------------+-----------------------------+---------------------+
| Scalp &Post Auricular                                                        | C44.41    | C44.42                                                 | D04.4                                  | C44.49                      |                     |
+------------------------------------------------------------------------------+-----------+--------------------------------------------------------+----------------------------------------+-----------------------------+---------------------+
| Trunk/Chest/Abdomen/Back                                                     | C44.519   | C44.529                                                | D04.5                                  | C44.599                     |                     |
+------------------------------------------------------------------------------+-----------+--------------------------------------------------------+----------------------------------------+-----------------------------+---------------------+
| Lower Limb (Left) (Including Hip)                                            | C44.719   | C44.729                                                | D04.72                                 | C44.799                     |                     |
+------------------------------------------------------------------------------+-----------+--------------------------------------------------------+----------------------------------------+-----------------------------+---------------------+
| Lower Limb (Right) (Including Hip)                                           | C44.712   | C44.722                                                | D04.71                                 | C44.792                     |                     |
+------------------------------------------------------------------------------+-----------+--------------------------------------------------------+----------------------------------------+-----------------------------+---------------------+
| Upper Limb (Left) (including Shoulder)                                       | C44.619   | C44.629                                                | D04.62                                 | C44.699                     |                     |
+------------------------------------------------------------------------------+-----------+--------------------------------------------------------+----------------------------------------+-----------------------------+---------------------+
| Upper Limb (Right) (including Shoulder)                                      | C44.612   | C44.622                                                | D04.61                                 | C44.692                     |                     |
+------------------------------------------------------------------------------+-----------+--------------------------------------------------------+----------------------------------------+-----------------------------+---------------------+
| Eyelids:                                                                     | C44.1121  | C44.1221                                               | D04.111                                | C44.1992                    |                     |
+------------------------------------------------------------------------------+-----------+--------------------------------------------------------+----------------------------------------+-----------------------------+---------------------+
| Eyelid (Right Upper) Eyelid (Right Lower)including Canthus                   | C44.1122  | C44.1222                                               | D04.112                                | C44.1991                    |                     |
+------------------------------------------------------------------------------+-----------+--------------------------------------------------------+----------------------------------------+-----------------------------+---------------------+
| Eyelid (Left Upper)                                                          | C44.1191  | C44.1291                                               | D04.121                                | C44.1922                    |                     |
+------------------------------------------------------------------------------+-----------+--------------------------------------------------------+----------------------------------------+-----------------------------+---------------------+
| Eyelid (Left Lower) including Canthus                                        | C44.1192  | C44.1292                                               | D04.122                                | C44.1921                    |                     |
+------------------------------------------------------------------------------+-----------+--------------------------------------------------------+----------------------------------------+-----------------------------+---------------------+
| Unspecified Parts of Face (Find More Specific Fit)                           | C44.310   | C44.320                                                | D04.30                                 |                             |                     |
+------------------------------------------------------------------------------+-----------+--------------------------------------------------------+----------------------------------------+-----------------------------+---------------------+
| Unspecified Codes (Find More Specific Fit)                                   | C44.91    | C44.92                                                 | D04.9                                  |                             |                     |
+------------------------------------------------------------------------------+-----------+--------------------------------------------------------+----------------------------------------+-----------------------------+---------------------+
| Unspecified Eyelid (Find More Specific Fit)                                  | C44.111   | C44.121                                                | D04.10                                 |                             |                     |
+------------------------------------------------------------------------------+-----------+--------------------------------------------------------+----------------------------------------+-----------------------------+---------------------+
<<<
RELATIONS:
- TYPE: Parent
  VALUE: RQ-H10SG-345
  ROLE: Refines
- TYPE: Parent
  VALUE: RQ-H10SG-740
  ROLE: Refines
- TYPE: Parent
  VALUE: RQ-H10SG-738
  ROLE: Refines

[DESIGN_ITEM]
UID: SW-H10SG-622
TITLE: User Login Sequence
STATEMENT: >>>
1. The user is presented with username and password.
2. AuthService validates the credentials against the persisted account. Incorrect passwords for unlocked accounts increment the persisted failed-login count; accounts at or above 10 failures reject login even with a correct password. Restart does not clear the count.
3. The server persists the login outcome security record without passwords or tokens. An audit persistence error fails closed without issuing a session. Authentication failures are presented to the user.
4. A valid login below the threshold resets the failed-login count to zero. Only after the outcome is persisted does the application configure AuthorizedUser with the issued auth token and user information and close the login screen.
<<<
RELATIONS:
- TYPE: Parent
  VALUE: RQ-H10SG-74
  ROLE: Refines
- TYPE: Parent
  VALUE: RQ-H10SG-648
  ROLE: Refines

[DESIGN_ITEM]
UID: SW-H10SG-623
TITLE: Disable Treatment when the Patient's Plan is Inconsistent
STATEMENT: >>>
Sequence Diagram:
Sequence Diagram:

.. raw:: html

   <pre class="mermaid">
   sequenceDiagram
       autonumber
       participant PrescriptionModel
       participant PlanViewModel
       participant CollimatorModel
       participant PlanModel

       PrescriptionModel->>PlanViewModel: Prescription changed
       activate PlanViewModel
       PlanViewModel->>PlanModel: fetch latest plan
       activate PlanModel
       
       Note over PlanModel: fetch plan data
       PlanModel-->>PlanViewModel: plan
       deactivate PlanModel
       
       PlanViewModel->>CollimatorModel: get active collimator
       CollimatorModel-->>PlanViewModel: 
       
       Note over PlanViewModel: check collimator

       alt collimator mismatch
           Note over PlanViewModel: disable treatment
           Note over PlanViewModel: show message
       end
       deactivate PlanViewModel
   </pre>
<<<
RELATIONS:
- TYPE: Parent
  VALUE: RQ-H10SG-14
  ROLE: Refines
- TYPE: Parent
  VALUE: RQ-H10SG-15
  ROLE: Refines
- TYPE: Parent
  VALUE: RQ-H10SG-191
  ROLE: Refines

[DESIGN_ITEM]
UID: SW-H10SG-624
TITLE: Patient's treatment fields Audit Trial
STATEMENT: >>>
Sequence Diagram for saving audit for Plan and Treatment Fields creation
<<<
RELATIONS:
- TYPE: Parent
  VALUE: RQ-H10SG-16
  ROLE: Refines

[DESIGN_ITEM]
UID: SW-H10SG-625
TITLE: Approve Patient's Treatment Fields (Plan)
STATEMENT: >>>
Sequence diagram for 'approve plan' use case:

Approval credential validation honors the persisted account lockout threshold but neither increments nor resets failed-login attempts. Rejected approval credentials leave the plan unchanged.

.. raw:: html

   <pre class="mermaid">
   sequenceDiagram
    actor User
    
    box rgb(245, 245, 245) Application
        participant PlanViewModel
        participant PlanModel
    end
    
    box rgb(245, 245, 245) Server
        participant Storage
    end

    User->>PlanViewModel: change plan status
    PlanViewModel->>User: show dialog
    User->>PlanViewModel: credentials & desired status
    
    PlanViewModel->>Storage: authenticate user
    activate Storage
    Storage->>Storage: handle request
    Storage-->>PlanViewModel: response
    deactivate Storage
    
    alt successful authentication
        PlanViewModel->>PlanModel: change plan status
        
        PlanModel->>Storage: save changes
        activate Storage
        Storage->>Storage: save plan
        Storage-->>PlanModel: saved plan
        deactivate Storage
    end
   </pre>
<<<
RELATIONS:
- TYPE: Parent
  VALUE: RQ-H10SG-17
  ROLE: Refines

[DESIGN_ITEM]
UID: SW-H10SG-626
TITLE: Refresh Patient's Treatment Fields from the database
STATEMENT: >>>

.. raw:: html

   <pre class="mermaid">
   sequenceDiagram
       autonumber
       actor User

       box Application
           participant PlanViewModel
           participant PlanModel
       end

       box Server
           participant Storage
       end

       User->>PlanViewModel: refresh treatment fields
       activate PlanViewModel
       PlanViewModel->>PlanModel: fetch fields
       activate PlanModel
       
       Note over PlanModel: clear displayed fields
       PlanModel->>Storage: query stored fields
       activate Storage
       Note over Storage: handle request
       Storage-->>PlanModel: treatment fields
       deactivate Storage
       
       Note over PlanModel: update displayed fields
       PlanModel-->>PlanViewModel: 
       PlanViewModel-->>User: display fields

       PlanViewModel->>PlanModel: validate field doses
       Note over PlanModel: verify dose calculations
       PlanModel-->>PlanViewModel: validity status
       deactivate PlanModel

       alt validation fails
           Note over PlanViewModel: disable treatment
           PlanViewModel-->>User: show warning
       end
       deactivate PlanViewModel
   </pre>

Fulfilled requirements:
- RQ-H10SG-18-#9: Patients - Plan view - Refresh Patient's Treatment Fields from the database
- RQ-H10SG-21-#11: Patients - Plan view - View Patient's Plan's Treatment Fields
<<<
RELATIONS:
- TYPE: Parent
  VALUE: RQ-H10SG-162
  ROLE: Refines

[DESIGN_ITEM]
UID: SW-H10SG-628
TITLE: Update Patient's Treatment Fields for a Plan
STATEMENT: >>>
Update patient's treatment fields:
1. If the plan is not approved, a read-only plan is displayed.
2. Otherwise, emission duration input is enabled.
3. User selects fields.
4. If a single field is selected, the delete button is enabled.
5. Otherwise, the add button or update and delete buttons are enabled depending on if it is an existing plan field.
<<<
RELATIONS:
- TYPE: Parent
  VALUE: RQ-H10SG-192
  ROLE: Refines

[DESIGN_ITEM]
UID: SW-H10SG-629
TITLE: Search Filtering
STATEMENT: >>>
The application shall provide search and filtering capabilities in the system logs view to allow operators to find and view specific log entries. The search and filtering functionality shall enable filtering by various criteria to help locate relevant system events.

The sequence diagram for the search filtering process is provided in the attached diagram.

.. raw:: html

   <pre class="mermaid">
   sequenceDiagram
       autonumber
       actor User

       box Application
           participant LogViewModel
           participant CreateFilterDialog
       end

       alt adding a filter
           User->>LogViewModel: add filter
           activate LogViewModel
           LogViewModel->>CreateFilterDialog: show dialog
           activate CreateFilterDialog
           CreateFilterDialog-->>User: select field to filter
           User->>CreateFilterDialog: selected field
           CreateFilterDialog-->>User: select message type
           User->>CreateFilterDialog: selected type
           CreateFilterDialog-->>LogViewModel: 
           deactivate CreateFilterDialog
           
           Note over LogViewModel: add new filter
           LogViewModel-->>User: updated list of records
           deactivate LogViewModel
       end

       alt removing a filter
           User->>LogViewModel: remove chosen filter
           activate LogViewModel
           Note over LogViewModel: remove the filter
           LogViewModel-->>User: updated list of records
           deactivate LogViewModel
       end
   </pre>

Fulfilled requirements:
- RQ-H10SG-22-#9: System Logs' View - Search Filtering

Attachments:
- H10SG-22.sequence.mermaid.drawio.png (121.61 kB)
<<<
RELATIONS:
- TYPE: Parent
  VALUE: RQ-H10SG-67
  ROLE: Refines

[DESIGN_ITEM]
UID: SW-H10SG-630
TITLE: Editing Patient's Prescription
STATEMENT: >>>
The application shall allow operators to edit and modify a patient's prescription within the treatment planning interface. The prescription editing functionality enables updates to prescription parameters and details associated with a patient's treatment plan.

The operator shall be able to modify prescription details and have these changes reflected in the patient's treatment plan.

.. raw:: html

    <pre class="mermaid">
    graph TD
        A[Prescription update] --> B{Simulation exists?}
        B -- No --> C[Empty form, disable all buttons]
        B -- Yes --> D[Enable Add button]
        D --> E{Prescription exists?}
        E -- Yes --> F[Fill the form]
        E -- No --> G[User clicks Add]
        G --> H[Create blank prescription]
        H --> F
        F --> I{Prescription is approved?}
        I -- Yes --> J[Readonly form]
        I -- No --> K[Enable form inputs]
        K --> L[User edits the form]
        L --> M[Enable Save and Refresh buttons]
    </pre>

Fulfilled requirements:
- RQ-H10SG-23-#9: Patients - Plan View - Edit Patient's Prescription
<<<
RELATIONS:
- TYPE: Parent
  VALUE: RQ-H10SG-23
  ROLE: Refines
- TYPE: Parent
  VALUE: RQ-H10SG-331
  ROLE: Refines

[DESIGN_ITEM]
UID: SW-H10SG-631
TITLE: view patient's prescription
STATEMENT: >>>
The application shall provide the ability for authorized users to view the patient's prescription information. The prescription view shall display relevant treatment prescription details associated with the patient's treatment plan.

The operator shall be able to access and review the prescription details for a patient through the patient's treatment plan view.

.. raw:: html

   <pre class="mermaid">
   sequenceDiagram
       autonumber
       
       box Application
           participant SimulationModel
           participant PrescriptionViewModel
           participant PrescriptionModel
           participant IEmrPrescriptionCommands
       end
       
       box Server
           participant PrescriptionService
       end

       Note over SimulationModel, IEmrPrescriptionCommands: User selects a site or changes its simulation
       
       SimulationModel-->>PrescriptionViewModel: simulation changed
       activate PrescriptionViewModel
       
       alt existing simulation
           PrescriptionViewModel->>PrescriptionModel: fetch prescription
           activate PrescriptionModel
           PrescriptionModel->>IEmrPrescriptionCommands: fetch simulation's prescriptions
           activate IEmrPrescriptionCommands
           
           IEmrPrescriptionCommands->>PrescriptionService: grpc:ListPrescriptionsRequest
           activate PrescriptionService
           Note over PrescriptionService: handle request
           PrescriptionService-->>IEmrPrescriptionCommands: grpc:ListPrescriptionsResponse
           deactivate PrescriptionService
           
           IEmrPrescriptionCommands-->>PrescriptionModel: list of prescriptions
           deactivate IEmrPrescriptionCommands
           
           Note over PrescriptionModel: select latest prescription
           PrescriptionModel-->>PrescriptionViewModel: [optional] prescription
           deactivate PrescriptionModel
           
           Note over PrescriptionViewModel: update prescription form
       end
       deactivate PrescriptionViewModel
   </pre>

Fulfilled requirements:
- RQ-H10SG-24-#12: Patients - Plan view - view patient's prescription
<<<
RELATIONS:
- TYPE: Parent
  VALUE: RQ-H10SG-24
  ROLE: Refines

[DESIGN_ITEM]
UID: SW-H10SG-632
TITLE: Sorting patient's list view
STATEMENT: >>>
.. raw:: html

   <pre class="mermaid">
   graph TD
       A[Plan update] --> B{Plan is approved?}
       B -- Yes --> C[Show readonly plan]
       B -- No --> D[Enable emission duration input]
       D --> E[/User selects fields/]
       E --> F{Single field selected?}
       F -- No --> G[Enable delete button]
       F -- Yes --> H{Existing plan field?}
       H -- Yes --> I[Enable update and delete buttons]
       H -- No --> J[Enable add button]
   </pre>

Note: The design specification for sorting patient's list view is not available. This appears to be a placeholder item. Refer to the requirements for SW-H10SG-632 for expected functionality.
<<<
RELATIONS:
- TYPE: Parent
  VALUE: RQ-H10SG-39
  ROLE: Refines

[DESIGN_ITEM]
UID: SW-H10SG-633
TITLE: Create new patient
STATEMENT: >>>
The application shall provide functionality for authorized users to create and register new patients in the system. The patient creation process shall include:

- A patient registration form with all required fields
- Validation of mandatory fields before saving
- Data integrity checking for input data
- Patient de-duplication to prevent duplicate patient entries
- User feedback on successful registration or error conditions
- Cancel and Save buttons for form control
- Support for editing patient demographic data

Fulfilled requirements:
- RQ-H10SG-47-#7: Patients - Patient's Registration Form - Cancel Button
- RQ-H10SG-48-#8: Patients - Patient's Registration Form - Save button
- RQ-H10SG-49-#11: Patients - Patient's Registration Form - Patient Already Exist Error
- RQ-H10SG-50-#10: Patients - Patients Registration Feedback
- RQ-H10SG-51-#6: Patients - Patients Registration Form - Mandatory Fields
- RQ-H10SG-52-#13: Patients - Patients Registration Form - Input Data Integrity
- RQ-H10SG-83-#10: Patients - Edit Patient Demographic Data
- RQ-H10SG-86-#18: Patients - Patient's Registration Form - Layout
<<<
RELATIONS:
- TYPE: Parent
  VALUE: RQ-H10SG-47
  ROLE: Refines
- TYPE: Parent
  VALUE: RQ-H10SG-48
  ROLE: Refines
- TYPE: Parent
  VALUE: RQ-H10SG-49
  ROLE: Refines
- TYPE: Parent
  VALUE: RQ-H10SG-50
  ROLE: Refines
- TYPE: Parent
  VALUE: RQ-H10SG-51
  ROLE: Refines
- TYPE: Parent
  VALUE: RQ-H10SG-52
  ROLE: Refines
- TYPE: Parent
  VALUE: RQ-H10SG-83
  ROLE: Refines
- TYPE: Parent
  VALUE: RQ-H10SG-86
  ROLE: Refines

[DESIGN_ITEM]
UID: SW-H10SG-671
TITLE: Mapping Pathology Enum to UI Description
STATEMENT: >>>
The dropdown control of Field Pathology should show the following list based on the Pathology Enum IDs:

+-------------------------------+--------------------------------+--------+
| Description (UI Label)        | Name                           | number |
+===============================+================================+========+
| Infundibulo-cytic             | Infundibulo_cytic              | 1      |
+-------------------------------+--------------------------------+--------+
| Ulcerated long-standing       | Ulcerated_long_standing        | 2      |
+-------------------------------+--------------------------------+--------+
| Adenosquamous                 | Adenosquamous                  | 3      |
+-------------------------------+--------------------------------+--------+
| Desmoplastic/Metaplastic      | Desmoplastic_Metaplastic       | 4      |
+-------------------------------+--------------------------------+--------+
| Recurrent Lesion post-surgery | Recurrent_Lesion_post_surger y | 5      |
+-------------------------------+--------------------------------+--------+
| Large Lesion                  | Large_Lesion                   | 6      |
+-------------------------------+--------------------------------+--------+
| Deep Lesion                   | Deep_Lesion                    | 7      |
+-------------------------------+--------------------------------+--------+
| Rapid growth                  | Rapid_growth                   | 8      |
+-------------------------------+--------------------------------+--------+
| Extention into hair follicle  | Extention_into_hair_follicle   | 9      |
+-------------------------------+--------------------------------+--------+
<<<
RELATIONS:
- TYPE: Parent
  VALUE: RQ-H10SG-389
  ROLE: Refines

[DESIGN_ITEM]
UID: SW-H10SG-672
TITLE: Mapping Cell Type to applicable Sub cells
STATEMENT: >>>
Mapping between Pathology cell-type to applicable sub-type

+------------+---------------------------------+
| Cell Type: | Subtypes:                       |
+============+=================================+
| BCC        | Aberrant                        |
+------------+---------------------------------+
|            | Adenoid                         |
+------------+---------------------------------+
|            | Atypical Basaloid Proliferation |
+------------+---------------------------------+
<<<
RELATIONS:
- TYPE: Parent
  VALUE: RQ-H10SG-386
  ROLE: Refines

[DESIGN_ITEM]
UID: SW-H10SG-673
TITLE: Mapping Pathology type to UI
STATEMENT: >>>
The Pathology should be mapped according to the returned Enum ID:

+--------------+----------------+----------+
| DB Enum Name | DB Enum Number | UI Label |
+==============+================+==========+
| 1            | BCC            | BCC      |
+--------------+----------------+----------+
| 2            | SCC            | SCC      |
+--------------+----------------+----------+
| 3            | SCC-IS         | SCC-IS   |
+--------------+----------------+----------+
| 4            | Keloid         | Keloid   |
+--------------+----------------+----------+
| Basosquamous | 5 Basosquamous |          |
+--------------+----------------+----------+
<<<
RELATIONS:
- TYPE: Parent
  VALUE: RQ-H10SG-385
  ROLE: Refines

[DESIGN_ITEM]
UID: SW-H10SG-674
TITLE: Mapping Site Location type to UI
STATEMENT: >>>
The Site(Field) Location should be mapped according to the returned Enum ID:

+--------------+----------------+------------+
| DB Enum Name | DB Enum Number | UI Label   |
+==============+================+============+
| Breast       | 1              | Breast     |
+--------------+----------------+------------+
| LeftEar      | 2              | Ear (Left) |
+--------------+----------------+------------+

+------------------+-----+----------------------+
| RightEar         | 3   | Ear (Right)          |
+==================+=====+======================+
| Forehead         | 4   | Forehead             |
+------------------+-----+----------------------+
| Temple           | 5   | Temple               |
+------------------+-----+----------------------+
| Zygoma           | 6   | Zygoma               |
+------------------+-----+----------------------+
| PreAuricular     | 7   | Pre-Auricular        |
+------------------+-----+----------------------+
| Cheek            | 8   | Cheek                |
+------------------+-----+----------------------+
| Chin             | 9   | Chin                 |
+------------------+-----+----------------------+
| Jaw              | 10  | Jaw                  |
+------------------+-----+----------------------+
| Lip              | 11  | Lip                  |
+------------------+-----+----------------------+
| Neck             | 12  | Neck                 |
+------------------+-----+----------------------+
| Nose             | 13  | Nose                 |
+------------------+-----+----------------------+
| Scalp            | 14  | Scalp                |
+------------------+-----+----------------------+
| PostAuricular    | 15  | Post Auricular       |
+------------------+-----+----------------------+
| Trunk            | 16  | Trunk                |
+------------------+-----+----------------------+
| Chest            | 17  | Chest                |
+------------------+-----+----------------------+
| Abdomen          | 18  | Abdomen              |
+------------------+-----+----------------------+
| Back             | 19  | Back                 |
+------------------+-----+----------------------+
| LeftLowerLimb    | 20  | Lower Limb (Left)    |
+------------------+-----+----------------------+
| RightLowerLimb   | 21  | Lower Limb (Right)   |
+------------------+-----+----------------------+
| LeftUpperLimb    | 22  | Upper Limb (Left)    |
+------------------+-----+----------------------+
| RightUpperLimb   | 23  | Upper Limb (Right)   |
+------------------+-----+----------------------+
| RightUpperEyelid | 24  | Eyelid (Right Upper) |
+------------------+-----+----------------------+
| RightLowerEyelid | 25  | Eyelid (Right Lower) |
+------------------+-----+----------------------+

+-----------------+-----+---------------------+
| LeftUpperEyelid | 26  | Eyelid (Left Upper) |
+=================+=====+=====================+
| LeftLowerEyelid | 27  | Eyelid (Left Lower) |
+-----------------+-----+---------------------+
<<<
RELATIONS:
- TYPE: Parent
  VALUE: RQ-H10SG-384
  ROLE: Refines

[DESIGN_ITEM]
UID: SW-H10SG-675
TITLE: Alert for unsaved data
STATEMENT: >>>
The application shall provide an alert mechanism to notify the user when they attempt to navigate away or close the application while there are unsaved changes in the patient's treatment plan view. This alert shall inform the user of unsaved data and provide options to save or discard changes.

Fulfilled requirements:
- RQ-H10SG-382-#6: Patients - Plan View - Alert for unsaved data
<<<
RELATIONS:
- TYPE: Parent
  VALUE: RQ-H10SG-382
  ROLE: Refines
- TYPE: Parent
  VALUE: RQ-H10SG-110
  ROLE: Refines

[DESIGN_ITEM]
UID: SW-H10SG-676
TITLE: Register and Update Collimator Flow
STATEMENT: >>>
1. Identify the connected collimator.

2. Open the New Collimator form with the serial of the identified collimator, or open the Edit Collimator form for a registered collimator.

3. When the user saves the form, the target-management view model passes the selected Active value to the collimator service. The service passes that value to the repository when creating a collimator and copies it to the updated collimator when editing one, so the repository persists the selected value in the Collimator table's ``IsActive`` field.

Before the collimator model is populated, the service fetches the active Head record. If none is active, the repository reactivates the existing Head with serial ``00000`` or, when that record does not exist, creates it as active with the current creation date. The resulting active Head is used as the foreign-key parent when a new collimator is saved. Head persistence requests include the creation date.
<<<
RELATIONS:
- TYPE: Parent
  VALUE: RQ-H10SG-126
  ROLE: Refines
- TYPE: Parent
  VALUE: RQ-H10SG-127
  ROLE: Refines
- TYPE: Parent
  VALUE: RQ-H10SG-383
  ROLE: Refines
- TYPE: Parent
  VALUE: RQ-H10SG-128
  ROLE: Refines

[DESIGN_ITEM]
UID: SW-H10SG-680
TITLE: New Collimator Mandatory Fields
STATEMENT: >>>
The Mandatory field of a Collimator should be:

- Serial - Automatically identified from telemetry.

- Type, Energy, and SSD should be fetched/saved from the Configuration Table.

Collimator Table

+----------------------------+---------+------------+-----------------------------------------------+
| Name                       | Type    | constraint | Description                                   |
+============================+=========+============+===============================================+
| ID                         | Int64   | Not Null   | Primary key. Auto incremental                 |
+----------------------------+---------+------------+-----------------------------------------------+
| HeadID                     | Int64   | Not Null   | Foreign Key to Head table                     |
+----------------------------+---------+------------+-----------------------------------------------+
| CollimatorConfigurati onID | Int64   | Not Null   | Foreign Key to CollimatorConfigurati on table |
+----------------------------+---------+------------+-----------------------------------------------+
| CreateDate                 | Date    | Not Null   |                                               |
+----------------------------+---------+------------+-----------------------------------------------+
| Serial                     | String  | Not Null   | Unique                                        |
+----------------------------+---------+------------+-----------------------------------------------+
| IsActive                   | Tinyint | Not Null   |                                               |
+----------------------------+---------+------------+-----------------------------------------------+

CollimatorConfiguration Table

+--------------------+----------------+------------+----------------------------------------------------------------+
| Name               | Type           | constraint | Description                                                    |
+====================+================+============+================================================================+
| ID                 | Int64          |            |                                                                |
+--------------------+----------------+------------+----------------------------------------------------------------+
| CreateDate         | DateTime       | Not Null   |                                                                |
+--------------------+----------------+------------+----------------------------------------------------------------+
| Type               | TargetTypeEnum | Not Null   | Unique with Energy and SSD                                     |
+--------------------+----------------+------------+----------------------------------------------------------------+
| Energy             | Energy Enum    | Not Null   | Unique with Type and SSD                                       |
+--------------------+----------------+------------+----------------------------------------------------------------+
| SSD                | SSDType Enum   | Not Null   | Unique with Type and Energy                                    |
+--------------------+----------------+------------+----------------------------------------------------------------+
| ReferencedDoseRate | Decimal        |            | Dose rate in the a specific cell in the collimator that serves |
+--------------------+----------------+------------+----------------------------------------------------------------+


<<<
RELATIONS:
- TYPE: Parent
  VALUE: RQ-H10SG-321
  ROLE: Refines

[DESIGN_ITEM]
UID: SW-H10SG-681
TITLE: Device ID Validation Flow
STATEMENT: >>>
The Device ID is mandatory for the application to be able to run. The application should validate the existence of the DeviceID on startup.

If no Device ID is present in settings, the user asked to enter such ID in a pop-up modal. The ID is saved to settings and presisted to the database.
<<<
RELATIONS:
- TYPE: Parent
  VALUE: RQ-H10SG-249
  ROLE: Refines

[DESIGN_ITEM]
UID: SW-H10SG-682
TITLE: Emission Current Calculation
STATEMENT: >>>
The Current should be auto-calculated as the quotient of Power[W] divided by Energy Level[kV]:

Emission Current[mA] = Power[W] / Voltage[kV]

The device shall operate at a constant power of 50W.

Here are the calculated values as a dependency on Energy Level:

+----------+-------------+----------------------+
| Power[W] | Voltage[kV] | Emission Current[mA] |
+==========+=============+======================+
| 50       | 50          | 1                    |
+----------+-------------+----------------------+
| 50       | 70          | 0.71                 |
+----------+-------------+----------------------+
| 50       | 100         | 0.5                  |
+----------+-------------+----------------------+
<<<
RELATIONS:
- TYPE: Parent
  VALUE: RQ-H10SG-232
  ROLE: Refines

[DESIGN_ITEM]
UID: SW-H10SG-683
TITLE: Calculate Emission Duration
STATEMENT: >>>
The Field Actual Dose should be auto-calculate from the duration using the following function:

[Field Output factor] * [Dose Rate cGy/min] * Duration / 60

i.e. 1.05 * 320 * 18 / 60 = 100.8 cGy

Field Output factor - This value should be retrieved from the OutputFactor service.

Dose Rate - This value should be retrieved from the CollimatorConfiguration Service.

Duration - This value is calculated from the [PrescribedDose] / ([FieldOutputFactor] * [DoseRate]) * 60
<<<
RELATIONS:
- TYPE: Parent
  VALUE: RQ-H10SG-231
  ROLE: Refines
- TYPE: Parent
  VALUE: RQ-H10SG-739
  ROLE: Refines

[DESIGN_ITEM]
UID: SW-H10SG-684
TITLE: Alert for an Invalid Plan when there are changes that affect its validity.
STATEMENT: >>>
The alert for an Invalid Plan will be triggered according to the following sequence diagram:

.. raw:: html

   <pre class="mermaid">
   sequenceDiagram
    actor A as Actor
    participant PrescriptionView
    participant PrescriptionViewModel

    A->>PrescriptionView: SavePrescription
    activate PrescriptionView
    
    PrescriptionView->>PrescriptionViewModel: SavePrescriptionAsync
    activate PrescriptionViewModel
    
    PrescriptionViewModel->>PrescriptionViewModel: CheckIfChangeAffectPlan
    activate PrescriptionViewModel
    deactivate PrescriptionViewModel
    
    PrescriptionViewModel->>PrescriptionViewModel: ShowMessageForUser (Plan will be delted)
    activate PrescriptionViewModel
    deactivate PrescriptionViewModel
    
    deactivate PrescriptionViewModel
    deactivate PrescriptionView
   </pre>
<<<
RELATIONS:
- TYPE: Parent
  VALUE: RQ-H10SG-162
  ROLE: Refines
- TYPE: Parent
  VALUE: RQ-H10SG-193
  ROLE: Refines

[DESIGN_ITEM]
UID: SW-H10SG-685
TITLE: Display Quality Checks Reports
STATEMENT: >>>
The quality check history shall include the following fields:
 - Timestamp
 - Performed by
 - Emission Current
 - Heater Current
 - Duration
 - Collimator configuration

The report will be retrieved from the database using the QcSampleService.

Each result row is keyed to a requested QA emission rather than a firmware point index. The
report presents its emission current, measured intensities, and deviations from the matching
reference result without creating rows for emissions that were not requested.
<<<
RELATIONS:
- TYPE: Parent
  VALUE: RQ-H10SG-190
  ROLE: Refines
- TYPE: Parent
  VALUE: RQ-H10SG-344
  ROLE: Refines

[DESIGN_ITEM]
UID: SW-H10SG-686
TITLE: Lock application during active emission
STATEMENT: >>>
The application will be locked when a user loads a plan in the external application.
The application will use the Plan DB Event to determine when such a plan is loaded.
<<<
RELATIONS:
- TYPE: Parent
  VALUE: RQ-H10SG-187
  ROLE: Refines

[DESIGN_ITEM]
UID: SW-H10SG-687
TITLE: Load For Treatment Flow
STATEMENT: >>>
When a user loads a plan in the external application, the plan service persists the Pending plan and publishes it to both the ``PlanEvents`` and ``LoadForTreatmentEvents`` streams.

Each stream uses a broadcast event hub with an independent queue for every active subscriber. Publishing writes the same event to every subscriber instead of allowing subscribers to compete for one shared channel item. Stream cancellation removes that subscriber's queue.

The external application loads the plan from its load-for-treatment event. Every internal application subscribed to the plan event receives the same update and locks its plan screen.

For an incomplete treatment, the internal application prompts the user to choose the
remaining scalar emission or the complete scalar emission before publishing the selected
plan. The external application recalculates the scalar treatment time from the latest
treatment completion status.

The shared treatment-plan validation runs before a plan is accepted for load. It permits
one valid treatment field and rejects missing, additional, or invalid fields before the
firmware-session preparation path receives the plan.
<<<
RELATIONS:
- TYPE: Parent
  VALUE: RQ-H10SG-184
  ROLE: Refines
- TYPE: Parent
  VALUE: RQ-H10SG-185
  ROLE: Refines
- TYPE: Parent
  VALUE: RQ-H10SG-422
  ROLE: Refines

[DESIGN_ITEM]
UID: SW-H10SG-688
TITLE: Update Collimator Data Flow Diagram
STATEMENT: >>>
The application will send an update command to the Collimator Service. The following flow describes the flow:

1. User edits collimator.
2. Collimator form is opened.
3. Upon save, collimator configuration is persisted to the database using CollimatorCommands.
<<<
RELATIONS:
- TYPE: Parent
  VALUE: RQ-H10SG-128
  ROLE: Refines

[DESIGN_ITEM]
UID: SW-H10SG-689
TITLE: User Management and Reset Lockout
STATEMENT: >>>
1. The user requests to add a new user.
2. The user add form is cleared and enabled.
3. The form is validated. If validation fails, saving is disabled and the error is presented to the user.
4. The new user record is presisted to the database.

User Management displays the persisted failed-login count as lock status. Reset lockout is enabled only for a locked selection and an authenticated Administrator with an active, unlocked, unexpired session. The confirmed command calls ResetUserLockout with the target user ID through the user commands/repository transport, handles errors using the existing task/dialog flow, and refreshes the list after completion.

ResetUserLockout resolves the bearer token through the server's session registry, then reloads the actor and role from persisted storage. Only the exact built-in Administrator role on an existing, unlocked actor authorizes the operation; a supplied user ID or stale client role alone is not authority. Missing, forged, deleted, demoted, locked, and non-administrator actors are rejected.

For a target at or above 10 failed login attempts, one transaction sets only failed_login_attempts to zero and writes the reset-success security record with actor and target IDs. Failure to persist the audit rolls back the reset. The response contains the target user; a target below 10 is returned unchanged with no reset-success record. Password, last_accessed, and other user fields are preserved, and the client adds no duplicate success audit. Ordinary CRUD retains the output-only counter contract.
<<<
RELATIONS:
- TYPE: Parent
  VALUE: RQ-H10SG-68
  ROLE: Refines
- TYPE: Parent
  VALUE: RQ-H10SG-125
  ROLE: Refines
- TYPE: Parent
  VALUE: RQ-H10SG-619
  ROLE: Refines
- TYPE: Parent
  VALUE: RQ-H10SG-618
  ROLE: Refines

[DESIGN_ITEM]
UID: SW-H10SG-690
TITLE: Save Endpoint Configuration Flow Diagram
STATEMENT: >>>
After the user saves endpoint configuration successfully, the application records the acting user and changed configuration identifiers through the action audit service. Cancelled edits, failed saves, unchanged values, automatic loads, and background RPC traffic do not produce successful configuration-change audit records.
<<<
RELATIONS:
- TYPE: Parent
  VALUE: RQ-H10SG-124
  ROLE: Refines

[DESIGN_ITEM]
UID: SW-H10SG-691
TITLE: Import Configuration From CSV file
STATEMENT: >>>
The application will import machine configuration from CSV file. The Data imported will be validated. 
Each collimator specified in the CSV file will have its configuration loaded from the database via the CollimatorConfigurationService.
The collimator configuration will then be updated from the CSV file parameters and then persisted to the database.
<<<
RELATIONS:
- TYPE: Parent
  VALUE: RQ-H10SG-115
  ROLE: Refines
- TYPE: Parent
  VALUE: RQ-H10SG-121
  ROLE: Refines

[DESIGN_ITEM]
UID: SW-H10SG-692
TITLE: Configuring Output Factors
STATEMENT: >>>
Output Factors hould support multiple collimators.

<<<
RELATIONS:
- TYPE: Parent
  VALUE: RQ-H10SG-332
  ROLE: Refines

[DESIGN_ITEM]
UID: SW-H10SG-693
TITLE: Update Output Factor Sequence
STATEMENT: >>>
The output factor of the reference field is the collimator's dose rate.
The output factor shall be persisted to the database via OutputFactorCommands.
<<<
RELATIONS:
- TYPE: Parent
  VALUE: RQ-H10SG-114
  ROLE: Refines

[DESIGN_ITEM]
UID: SW-H10SG-694
TITLE: Output Factor Configuration Flow
STATEMENT: >>>
1. The user selects a collimator configuration.
2. The application requests configuration data via the OutputFactorService.
<<<
RELATIONS:
- TYPE: Parent
  VALUE: RQ-H10SG-118
  ROLE: Refines
- TYPE: Parent
  VALUE: RQ-H10SG-119
  ROLE: Refines
- TYPE: Parent
  VALUE: RQ-H10SG-120
  ROLE: Refines

[DESIGN_ITEM]
UID: SW-H10SG-695
TITLE: Heater Current Configuration Sequence
STATEMENT: >>>
The application shall store the heater current in the database. When the user changes the heater current, it shall be validated before saving. Validation errors shall be presented to the user.

When retrieving the current configuration, if no such configuration exists, a configuration record shall be created.
<<<
RELATIONS:
- TYPE: Parent
  VALUE: RQ-H10SG-112
  ROLE: Refines

[DESIGN_ITEM]
UID: SW-H10SG-696
TITLE: Configure Correction Matrix for Magnetometer
STATEMENT: >>>
.. raw:: html

   <pre class="mermaid">
   sequenceDiagram
    box rgb(245, 245, 245) Application
        participant ConfigurationViewModel
        participant MagnetometerViewMode
        participant MagnetometerCorrections
        participant IReferenceFieldCommands
        participant ICorrectionMatrixCommands
    end
    
    box rgb(245, 245, 245) Server
        participant ReferenceFieldService
        participant CorrectionMatrixService
    end

    Note over ConfigurationViewModel: User selects a collimator configuration
    
    activate ConfigurationViewModel
    ConfigurationViewModel->>MagnetometerCorrections: fetch configuration data
    activate MagnetometerCorrections
    
    MagnetometerCorrections->>IReferenceFieldCommands: read reference fields by preset id
    activate IReferenceFieldCommands
    
    IReferenceFieldCommands->>ReferenceFieldService: grpc:ListReferneceFieldsRequest
    activate ReferenceFieldService
    
    ReferenceFieldService->>ReferenceFieldService: handle request
    ReferenceFieldService-->>IReferenceFieldCommands: grpc:ListReferneceFieldsResponse
    deactivate ReferenceFieldService
    
    IReferenceFieldCommands-->>MagnetometerCorrections: list of reference field records
    deactivate IReferenceFieldCommands
    
    MagnetometerCorrections->>ICorrectionMatrixCommands: read correction matrices by preset id
    activate ICorrectionMatrixCommands
    
    ICorrectionMatrixCommands->>CorrectionMatrixService: grpc:ListCorrectionMatricesRequest
    activate CorrectionMatrixService
    
    CorrectionMatrixService->>CorrectionMatrixService: handle request
    CorrectionMatrixService-->>ICorrectionMatrixCommands: grpc:ListCorrectionMatricesResponse
    deactivate CorrectionMatrixService
    
    ICorrectionMatrixCommands-->>MagnetometerCorrections: list of correction matrix records
    deactivate ICorrectionMatrixCommands
    
    MagnetometerCorrections->>MagnetometerCorrections: update configuration
    
    MagnetometerCorrections-->>MagnetometerViewMode: configuration changed
    deactivate MagnetometerCorrections
    deactivate ConfigurationViewModel
   </pre>
<<<
RELATIONS:
- TYPE: Parent
  VALUE: RQ-H10SG-111
  ROLE: Refines

[DESIGN_ITEM]
UID: SW-H10SG-698
TITLE: Retrieve Treatment History Sequence
STATEMENT: >>>
Sequence diagram for retrieving treatment history when the selected plan changes:

.. raw:: html

   <pre class="mermaid">
   sequenceDiagram
    box rgb(245, 245, 245) Application
        participant TreatmentsViewModel
        participant TreatmentHistoryModel
        participant IEmrTreatmentCommands
        participant IEmrActualTreatmentFieldCommands
    end

    box rgb(245, 245, 245) Server
        participant TreatmentService
        participant TreatmentFieldService
    end

    Note over TreatmentsViewModel: TreatmentInfoStore.PlanChanged
    alt [different plan selected]
        TreatmentsViewModel->>TreatmentHistoryModel: SetContext(diagnosis, prescription, plan)
        TreatmentsViewModel->>TreatmentHistoryModel: FetchTreatmentsAsync()
    else [same plan refreshed]
        TreatmentsViewModel->>TreatmentHistoryModel: UpdateTreatmentsAsync()
    end
    activate TreatmentHistoryModel
    TreatmentHistoryModel->>IEmrTreatmentCommands: ReadListAsync(plan.Id)
    IEmrTreatmentCommands->>TreatmentService: grpc:ListTreatmentsRequest
    TreatmentService-->>IEmrTreatmentCommands: grpc:ListTreatmentsResponse
    IEmrTreatmentCommands-->>TreatmentHistoryModel: treatments
    loop [for each treatment in ID order]
        TreatmentHistoryModel->>IEmrActualTreatmentFieldCommands: ReadListAsync(treatment.Id)
        IEmrActualTreatmentFieldCommands->>TreatmentFieldService: grpc:ListActualTreatmentFieldsRequest
        TreatmentFieldService-->>IEmrActualTreatmentFieldCommands: grpc:ListActualTreatmentFieldsResponse
        IEmrActualTreatmentFieldCommands-->>TreatmentHistoryModel: actual treatment fields
        TreatmentHistoryModel->>TreatmentHistoryModel: map field display names and add treatment
    end
    TreatmentHistoryModel->>TreatmentHistoryModel: update treatment history and summary
    TreatmentHistoryModel-->>TreatmentsViewModel: observable data changed
    deactivate TreatmentHistoryModel
   </pre>
<<<
RELATIONS:
- TYPE: Parent
  VALUE: RQ-H10SG-94
  ROLE: Refines

[DESIGN_ITEM]
UID: SW-H10SG-699
TITLE: Display Actual Treatment Fields
STATEMENT: >>>
Actual treatment fields are retrieved with their parent treatment as shown in
``SW-H10SG-698``. The following sequence displays the fields for the treatment selected
by the user:

.. raw:: html

   <pre class="mermaid">
   sequenceDiagram
    participant TreatmentsView
    participant TreatmentsViewModel
    participant TreatmentHistoryModel

    Note over TreatmentsView,TreatmentHistoryModel: Treatment history and actual fields have already been loaded
    TreatmentsView->>TreatmentsViewModel: ShowActualFieldsCommand(treatment)
    TreatmentsViewModel->>TreatmentHistoryModel: SelectedTreatment = treatment
    TreatmentHistoryModel-->>TreatmentsView: property change exposes selected treatment fields
   </pre>
<<<
RELATIONS:
- TYPE: Parent
  VALUE: RQ-H10SG-95
  ROLE: Refines

[DESIGN_ITEM]
UID: SW-H10SG-700
TITLE: Create Patient's Treatment Simulation
STATEMENT: >>>
1. The user requests to add a simulation.
2. The simulation form is cleared and enabled.
3. The form is validated. If there is a validation error, the form is disabled and the user is presented the error.
4. The simulation and site simulation records are persisted to the database.
<<<
RELATIONS:
- TYPE: Parent
  VALUE: RQ-H10SG-89
  ROLE: Refines

[DESIGN_ITEM]
UID: SW-H10SG-701
TITLE: Retrieve Patient's Treatment Simulation
STATEMENT: >>>
Sequence diagram for retrieving the latest treatment simulation, its devices, and its
patient positions when the user selects a site or requests a refresh:

.. raw:: html

   <pre class="mermaid">
   sequenceDiagram
    participant SimulationViewModel
    participant SimulationRepository
    participant IEmrSimulationCommands
    participant IEmrTreatmentDeviceCommands
    participant IEmrPatientPositionCommands
    participant TreatmentInfoStore

    Note over SimulationViewModel: DiagnosisChanged, ReloadCommand, or PlanStatusChangedEvent
    SimulationViewModel->>SimulationRepository: FetchLatestSimulationAsync(diagnosis.Id)
    activate SimulationRepository
    SimulationRepository->>IEmrSimulationCommands: ReadListAsync(diagnosis.Id)
    IEmrSimulationCommands-->>SimulationRepository: simulations
    SimulationRepository->>SimulationRepository: select simulation with greatest ID
    SimulationRepository-->>SimulationViewModel: optional latest simulation
    deactivate SimulationRepository

    opt [simulation exists]
        SimulationViewModel->>SimulationRepository: FetchTreatmentDevicesAsync(simulation.Id)
        SimulationRepository->>IEmrTreatmentDeviceCommands: ReadListAsync(simulation.Id)
        IEmrTreatmentDeviceCommands-->>SimulationRepository: treatment devices
        SimulationRepository-->>SimulationViewModel: treatment devices

        SimulationViewModel->>SimulationRepository: FetchPatientPositionsAsync(simulation.Id)
        SimulationRepository->>IEmrPatientPositionCommands: ReadListAsync(simulation.Id)
        IEmrPatientPositionCommands-->>SimulationRepository: patient positions
        SimulationRepository-->>SimulationViewModel: patient positions
    end

    SimulationViewModel->>TreatmentInfoStore: SetSimulation(simulation, devices, positions)
    TreatmentInfoStore-->>SimulationViewModel: simulation data changed
    SimulationViewModel->>SimulationViewModel: update simulation form
   </pre>
<<<
RELATIONS:
- TYPE: Parent
  VALUE: RQ-H10SG-88
  ROLE: Refines

[DESIGN_ITEM]
UID: SW-H10SG-702
TITLE: Create Patient's Prescription Sequence
STATEMENT: >>>
1. When the user adds a prescription, the prescription form is cleared and enabled.
2. Entered prescription data is validated. If validation fails, saving is disabled and the user is presented the error.
3. The prescription and the simulation's prescription records are saved in the database.
<<<
RELATIONS:
- TYPE: Parent
  VALUE: RQ-H10SG-80
  ROLE: Refines

[DESIGN_ITEM]
UID: SW-H10SG-703
TITLE: Actual Treatment Delivered
STATEMENT: >>>
.. raw:: html

   <pre class="mermaid">
   sequenceDiagram
    box rgb(245, 245, 245) Application
        participant TreatmentViewModel
        participant TreatmentHistoryModel
        participant IEmrTreatmentCommands
        participant IEmrActualTreatmentFieldCommands
    end
    
    box rgb(245, 245, 245) Server
        participant TreatmentService
        participant TreatmentFieldService
    end

    Note over TreatmentViewModel,IEmrActualTreatmentFieldCommands: current plan changed or current treatment process finished
    
    TreatmentViewModel-->>TreatmentHistoryModel: fetch/update treatment data
    activate TreatmentHistoryModel
    
    TreatmentHistoryModel->>IEmrTreatmentCommands: fetch plan treatments
    activate IEmrTreatmentCommands
    
    IEmrTreatmentCommands->>TreatmentService: grpc: ListTreatmentsRequest
    activate TreatmentService
    
    TreatmentService->>TreatmentService: handle request
    TreatmentService-->>IEmrTreatmentCommands: grpc: ListTreatmentsResponse
    deactivate TreatmentService
    
    IEmrTreatmentCommands-->>TreatmentHistoryModel: list of treatments
    deactivate IEmrTreatmentCommands
    
    loop [for each treatment record]
        TreatmentHistoryModel->>IEmrActualTreatmentFieldCommands: fetch treatment fields
        activate IEmrActualTreatmentFieldCommands
        
        IEmrActualTreatmentFieldCommands->>TreatmentFieldService: grpc:ListActualTreatmentFieldsRequest
        activate TreatmentFieldService
        
        TreatmentFieldService->>TreatmentFieldService: handle request
        TreatmentFieldService-->>IEmrActualTreatmentFieldCommands: grpc:ListActualTreatmentFieldsResponse
        deactivate TreatmentFieldService
        
        IEmrActualTreatmentFieldCommands-->>TreatmentHistoryModel: list of actual fields
        deactivate IEmrActualTreatmentFieldCommands
        
        TreatmentHistoryModel->>TreatmentHistoryModel: sort fields and set to treatment
        TreatmentHistoryModel->>TreatmentHistoryModel: build treatment summary
        
        TreatmentHistoryModel-->>TreatmentViewModel: 
    end
    deactivate TreatmentHistoryModel
   </pre>
<<<
RELATIONS:
- TYPE: Parent
  VALUE: RQ-H10SG-94
  ROLE: Refines

[DESIGN_ITEM]
UID: SW-H10SG-705
TITLE: Save Patient Audit Log Records
STATEMENT: >>>
Sequence diagram for registering the current user and patient identifier once a requested patient change is successfully persisted. Failed, unchanged, reverted, or unapplied saves produce no successful-change audit. The record identifies the save operation, not demographic field values. Log persistence is queued and assigns the record timestamp.

Explicit navigation that displays a patient, diagnosis, simulation, prescription, or plan records the acting user and displayed record identifiers. Cached tab revisits and explicit returns to an already loaded record are views even without a database read; automatic navigation, background loads, and refreshes are not. A failed read is not recorded as a successful view of the unavailable record.

.. raw:: html

   <pre class="mermaid">
   sequenceDiagram
    box rgb(245, 245, 245) Application
        participant PatientsViewModel
        participant ActionAuditService
        participant DbLogRepository
        participant PatientEditing
        participant PatientListModel
        participant PatientRepository
    end

    box rgb(245, 245, 245) Server
        participant LogService
        participant PatientService
    end

    PatientsViewModel->>PatientEditing: SavePatientAsync()
    PatientEditing->>PatientListModel: SavePatientAsync(patient)
    alt [new patient]
        PatientListModel->>PatientRepository: CreateAsync(patient)
        PatientRepository->>PatientService: grpc:CreatePatient
        PatientService-->>PatientRepository: created patient
    else [existing patient]
        PatientListModel->>PatientRepository: UpdateAsync(old patient, new patient)
        PatientRepository->>PatientService: grpc:UpdatePatient
        PatientService-->>PatientRepository: updated patient
    end
    PatientRepository-->>PatientListModel: saved patient
    PatientListModel-->>PatientEditing: saved patient
    PatientEditing-->>PatientsViewModel: saved patient

    opt [requested change successfully persisted]
        PatientsViewModel->>ActionAuditService: RegisterAction(save completed with patient ID)
        ActionAuditService->>ActionAuditService: add current username and user ID
        ActionAuditService->>DbLogRepository: LogAsync(user audit record, not awaited)
        DbLogRepository->>LogService: CreateRecord
        LogService-->>DbLogRepository: persisted record with timestamp
    end
   </pre>
<<<
RELATIONS:
- TYPE: Parent
  VALUE: RQ-H10SG-45
  ROLE: Refines

[DESIGN_ITEM]
UID: SW-H10SG-708
TITLE: Display System Telemetry
STATEMENT: >>>
The receive-only GCB telemetry service passes unsolicited device-information, telemetry,
and fault datagrams to the system telemetry processor. The operating mode in device
information selects the corresponding normal or calibration parser. The selected parser
translates the complete physical interlock status and required-interlock masks into
``SystemInterlocks`` while retaining both raw masks for service diagnostics. The calibration
parser validates the expanded 55-field payload while preserving fields 0 through 46. It
maps the appended collimator-ID low and high words at fields 47 and 48, Mag 1 X/Y/Z at
fields 49 through 51, and Mag 2 X/Y/Z at fields 52 through 54 into the same semantic
snapshot properties as the normal parser.

Valid immutable snapshots are published through the main-board model and GCB data store;
unsupported modes or malformed packets do not replace the last valid snapshot. Publication
is limited to one snapshot every
250 ms, and 1.5 seconds without valid telemetry produces an unavailable snapshot.
System readiness requires a clear buffered master-fault input, no active system fault,
and all required interlocks to be available and active.
<<<
RELATIONS:
- TYPE: Parent
  VALUE: RQ-H10SG-54
  ROLE: Refines
- TYPE: Parent
  VALUE: RQ-H10SG-65
  ROLE: Refines

[DESIGN_ITEM]
UID: SW-H10SG-709
TITLE: Cancel Load For Treatment Flow
STATEMENT: >>>
The application is unlocked when a user cancels.
<<<
RELATIONS:
- TYPE: Parent
  VALUE: RQ-H10SG-186
  ROLE: Refines

[DESIGN_ITEM]
UID: SW-H10SG-710
TITLE: Show message for DB communication error
STATEMENT: >>>
The application will show a DB Communication error when the gRPC command throws a timeout exception. The exception will be populated through the MVVM model.
<<<
RELATIONS:
- TYPE: Parent
  VALUE: RQ-H10SG-162
  ROLE: Refines

[DESIGN_ITEM]
UID: SW-H10SG-711
TITLE: Retrieve Patients List
STATEMENT: >>>
The flow for retrieving the patient list should be implemented as described in the following sequence diagram:
<<<
RELATIONS:
- TYPE: Parent
  VALUE: RQ-H10SG-40
  ROLE: Refines
- TYPE: Parent
  VALUE: RQ-H10SG-50
  ROLE: Refines
- TYPE: Parent
  VALUE: RQ-H10SG-82
  ROLE: Refines
- TYPE: Parent
  VALUE: RQ-H10SG-37
  ROLE: Refines
- TYPE: Parent
  VALUE: RQ-H10SG-42
  ROLE: Refines

[DESIGN_ITEM]
UID: SW-H10SG-712
TITLE: Retrieve Patient's Fields (Sites)
STATEMENT: >>>
The flow for retrieving Patient's Fields ( Sites) should be implemented as described in the following sequence diagram:
<<<
RELATIONS:
- TYPE: Parent
  VALUE: RQ-H10SG-388
  ROLE: Refines

[DESIGN_ITEM]
UID: SW-H10SG-713
TITLE: Retrieve System Signals
STATEMENT: >>>
The detailed telemetry view binds to nullable semantic fields on the GCB data store's
latest immutable telemetry snapshot and renders unavailable firmware-specific fields as
not available. Its System section displays the raw interlock-input and required-interlock
masks for service diagnosis. The fault view binds to the store's latched active-fault list
and displays each formatted message with its captured state and runtime. Both views consume
store notifications and do not poll the firmware.
<<<
RELATIONS:
- TYPE: Parent
  VALUE: RQ-H10SG-65
  ROLE: Refines

[DESIGN_ITEM]
UID: SW-H10SG-714
TITLE: Calibration Mode Patient Lockout
STATEMENT: >>>
The indoor main-tabs view binds the Patients tab enabled state to the immutable telemetry
firmware mode. Calibration mode disables the tab. A high-z-order overlay inside the tab
obscures previously rendered patient content and displays the service-required message.
Unknown or unavailable firmware mode does not lock the tab.
<<<
RELATIONS:
- TYPE: Parent
  VALUE: RQ-H10SG-741
  ROLE: Refines

[DESIGN_ITEM]
UID: SW-H10SG-715
TITLE: Encrypted Local Database and Recovery Key
STATEMENT: >>>
Provider and key derivation

The embedded indoor database uses Microsoft.Data.Sqlite.Core 8.0.14 with SQLitePCLRaw.bundle_e_sqlcipher 2.1.11 on the existing Windows x64 target. SQLitePCL.Batteries_V2.Init initializes the provider once before any SQLite connection. Startup requires a nonempty ``PRAGMA cipher_version`` reporting major version 4; an absent or incompatible cipher fails closed without an ordinary-SQLite fallback. The ordinary Microsoft.Data.Sqlite bundle is not shipped or initialized alongside SQLCipher. This community native bundle is not an officially supported Zetetic binary or a FIPS-validated component.

The master encryption key (MEK) consists of 16 cryptographically random bytes, providing 128 bits of key entropy. The local database password is ``Convert.ToHexString(mek)``: the uppercase 32-character hexadecimal representation supplied as an ordinary SQLCipher passphrase, not raw-key ``x'...'`` syntax and not the numeric recovery display. SQLCipher 4 derives an AES-256 key using PBKDF2-HMAC-SHA512 and a database salt. The design retains 4096-byte pages, per-page HMAC-SHA512, and no plaintext header. It does not reduce KDF work or disable HMAC. A 256-bit derived AES key does not increase the random MEK's 128-bit entropy.

SqlCipherConnectionFactory builds a keyed connection string once, uses ReadWrite mode and pooling for runtime connections, and sets ``PRAGMA temp_store=MEMORY`` before application SQL. Missing runtime database files are not silently recreated. Failed opens dispose their connections. Initialization and transfers use explicitly created or read-only non-pooled connections. All protobuf repositories use this factory; the host eagerly initializes every registered repository before starting its listener, preserving existing schema, CRUD, parent-column migration, and approval behavior without a separate schema registry or metadata table.

Encrypted private validation connections are opened without a connection-string Password, then keyed with a safely quoted PRAGMA key before database access. Deliberately plaintext connections omit PRAGMA key. This gives the application ownership of the native handle before a wrong key can fail schema validation; Microsoft.Data.Sqlite's connection-string password validation can otherwise fail during construction and defer handle release to garbage collection. Failed recovery or backup-password attempts therefore close their handles deterministically.

Files and the Windows protector

Paths are resolved under the configured GBSKMainSettings.StorageRoot, whose default is ``C:/HERACLES/DATA/``. The live file is ``heracles.encrypted.db``, the protector is ``heracles.db.key``, and the development-only plaintext source is ``heracles.db``. Under the default root these are ``C:/HERACLES/DATA/heracles.encrypted.db``, ``C:/HERACLES/DATA/heracles.db.key``, and ``C:/HERACLES/DATA/heracles.db`` respectively.

DpapiKeyStore uses System.Security.Cryptography.ProtectedData 8.0.0 to protect exactly the 16 MEK bytes with Windows DPAPI CurrentUser scope and null optional entropy. Only the binary protected blob is stored at the key path. Save writes a same-directory temporary protected blob and replaces the protector; no plaintext MEK file is written. Load uses the same scope and entropy. A missing blob, DPAPI cryptographic failure, or unprotected length other than 16 bytes means that no usable key was supplied. Access, permissions, disk, and other I/O failures instead propagate as sanitized operational startup errors, not instructions to generate a replacement key. Temporary key buffers are zeroed with CryptographicOperations.ZeroMemory; disposing SqlCipherDatabase clears its owned MEK bytes and releases its connection pool.

The recovery display

RecoveryKeyCodec splits the MEK, in byte order, into eight unsigned big-endian 16-bit integers. Each integer is multiplied by 11 and formatted as exactly six invariant-culture ASCII decimal digits; groups are joined by ASCII hyphens. For the controlled fixed vector ``00000001000A00FF01000FFF8000FFFF``, the display is ``000000-000011-000110-002805-002816-045045-360448-720885``.

Parsing trims only surrounding whitespace and requires exactly eight six-digit groups separated by hyphens, with ASCII digits only. Each value must be between 0 and 720885 inclusive and divisible by 11. Division by 11 restores the corresponding two big-endian bytes. Invalid input returns no key and is not included in an error message. This is a BitLocker-style 48-digit representation, not a BitLocker-compatible protector. The group check digits detect many transcription errors but do not authenticate a key. The numeric display is formatted on demand rather than cached.

Startup, provisioning, and recovery

1. In the UseSqliteDatabase startup branch, initialize SqlCipherDatabase and make the configured directory available before constructing the database host, channel, FieldModel, or telemetry consumers. Access failure terminates startup with a sanitized actionable message, without creating the shell. Non-SQLite branches retain their normal operation.

2. If the encrypted file exists, it is authoritative even when the development plaintext file also exists. Never generate a replacement MEK, merge, remigrate over it, or fall back to plaintext. Try the DPAPI MEK against a real ``SELECT count(*) FROM sqlite_master``. After a successful schema read, require ``PRAGMA cipher_integrity_check`` to return zero rows and ``PRAGMA integrity_check`` to return exactly ``ok``. A subsequent integrity failure is corruption: stop rather than offering overwrite or reinitialization.

3. If DPAPI supplies no usable MEK, or its MEK fails the initial schema read, request the numeric recovery key. Malformed input and a validly formatted but incorrect key receive a generic retry message; cancellation stops startup. The first prompt has no validation error. Test every candidate against the existing file and both full integrity checks before saving a new CurrentUser protector. Recovery attempts never change database bytes. On success the recovered MEK restores automatic unlock; it is not rotated.

4. If no encrypted database exists, reuse a valid DPAPI MEK left by an interrupted first initialization, or generate 16 bytes using RandomNumberGenerator.GetBytes. Before committing a new database or protector, display its formatted recovery key and require the explicit acknowledgement ``I have saved this recovery key``. Cancel leaves the development source untouched. Provisioning is an operator workflow before login, because application authentication depends on database access; it is distinct from the administrator-only Settings reveal.

5. Only after acknowledgement, save the DPAPI protector. If the development plaintext source exists, use the same keyed-copy primitive as database transfer: create the encrypted output and copy all source schema and data with sqlcipher_export, using an explicitly empty source key. Do not use PRAGMA rekey. Preserve IDs, hierarchy, indexes, triggers, database metadata, and AUTOINCREMENT high-water marks. Validate the reopened encrypted output and close all source and destination connections before deleting the development plaintext file and its own SQLite sidecars. Do not retain a plaintext backup. Without a plaintext source, use a non-pooled keyed Create connection and VACUUM to create a valid empty encrypted database; normal host initialization supplies its tables.

6. A failed migration removes only its incomplete output and retains the development source. No migration journal, rollback snapshot, or resumption protocol is introduced. A leftover protector is reused and shown again at the next no-database startup. Failure to delete a successfully migrated plaintext source prevents normal startup. A subsequent startup first fully validates the authoritative encrypted file, then retries cleanup of the remaining legacy source and sidecars. Deletion is not a secure-erasure guarantee.

The standalone pre-shell recovery window uses the shared WPF resources. Provisioning shows a selectable read-only key, acknowledgement, Continue, and Cancel; recovery shows key entry, Unlock, Cancel, and a local sanitized validation message. Closing either mode cancels. Explicit WPF shutdown mode is temporarily used while the window is displayed and then restored. The key never appears in a generic exception dialog. Exit cleanup tolerates partial initialization and disposes only objects actually initialized, without resolving unused database consumers.

Security boundaries

Possession of the MEK is the recovery authority before database-backed login is available. A copied encrypted database and its saved numeric MEK can be recovered under another Windows account or machine, creating a protector bound to that account; the copied CurrentUser blob alone cannot perform that unlock. Saving the recovery key externally is the provisioning operator's responsibility; the application does not automatically copy, print, or export it as plaintext.

Cryptographic page integrity detects unauthorized alteration but does not provide rollback or replay protection against replacement with an older authentic database. Application-role controls do not isolate keys from a process already running as the provisioning Windows account. SQLCipher diagnostics, SQL, connection strings, DPAPI buffers, passwords, and recovery keys are excluded from application logs, audit text, generic exception details, and command lines. Managed strings cannot be guaranteed erased and are retained only for the operation that needs them.
<<<
RELATIONS:
- TYPE: Parent
  VALUE: RQ-H10SG-55
  ROLE: Refines
- TYPE: Parent
  VALUE: RQ-H10SG-789
  ROLE: Refines
- TYPE: Parent
  VALUE: RQ-H10SG-790
  ROLE: Refines

[DESIGN_ITEM]
UID: SW-H10SG-716
TITLE: Administrator Data Management
STATEMENT: >>>
Availability, authorization, and secret display

Settings > Data Management retains the existing Settings/SystemSettings permission gate. Embedded-mode administrators with an active, unlocked, unexpired session can reveal the MEK recovery key, export, or import. DataManagementService is registered in every database mode, with embedded database and host objects optional; non-embedded mode reports unavailability and supplies no usable management controls. A non-administrator with Settings access sees an administrator-required message, not key or transfer controls.

Every service entry independently checks embedded availability, a non-null authorized user with Role.Name exactly equal to UserRole.BuiltInNames.Administrator, and a non-null IBearerTokenUserSessionManager.UserSession that is neither locked nor expired. UI command state uses the same predicate, with authorized-user and session-change notifications marshalled to the dispatcher. Retaining an AuthorizedUser after session expiry does not authorize a management call. No new role, permission field, credential reauthentication dialog, or management gRPC endpoint is introduced.

The MEK recovery key TextBox is read-only and initially contains only a fixed mask. A single eye-icon toggle reveals or hides it. Reveal obtains the display only after authorization; Hide removes the actual bound string rather than concealing it with color. Hide, view unload or tab departure, logout or user switch, lock or expiration, and the start of a transfer clear the revealed value. Returning to the tab always shows the mask. View-lifetime subscriptions are released appropriately. Recovery-key disclosure after login is administrator-only, separate from first provisioning and possession-based startup recovery.

A second read-only, selectable field beneath the recovery key exposes the 32-character uppercase hexadecimal MEK with the visible label and accessibility name ``Passphrase``. Administrators obtain this value through Settings > Data Management using the shared eye toggle and copy it securely for live database inspection; no manual conversion of the numeric recovery key is required. Use it as an ordinary passphrase with SQLCipher 4 settings, not as a derived raw encryption key or raw-key-mode value. The numeric recovery key remains the startup recovery credential, while an encrypted export uses its independently chosen export password rather than the local Passphrase. The Passphrase is obtained through the same administrator/session and busy-state guards and cleared back to its own fixed mask on every recovery-key hiding transition. Copying is a deliberate standard text-selection action; no automatic clipboard write is performed. Inspection procedures clear any controlled clipboard and secret input afterward and exclude secrets from logs, command lines, screenshots, and public evidence.

The nested settings view follows the existing Prism AutoWire pattern and uses BindableBase and DelegateCommand with explicit busy state and caught asynchronous errors. New settings and recovery surfaces use the application's existing shared theme and control styles. The password dialog uses DialogViewModelBase and PasswordBox controls, not the account-approval dialog or its error logging. Export requires matching confirmation; exactly empty password and confirmation select an unencrypted export. Import asks once and permits an empty password for plaintext input. Labels and help text do not instruct users to leave password fields empty. Nonempty whitespace-only passwords and embedded NUL are rejected locally; encryption passwords are used exactly as entered, without trimming, normalization, or extra complexity rules. Invalid or mismatched input keeps the dialog open with a local message. The password result is consumed immediately, and PasswordBox, view-model, and dialog-result references are cleared on every close path and in operation cleanup. No automatic clipboard action is performed.

Export uses a SaveFileDialog with overwrite confirmation, default extension .db, filter ``Database (*.db)|*.db``, and default filename ``heracles-backup-yyyyMMdd-HHmmss.db``. Import uses an OpenFileDialog with the same database filter, file-existence checking and single selection. Cancelling a file or password dialog is a no-op. Before import preparation, require explicit confirmation: ``Import replaces the entire database, including users and settings, and closes the application. Continue?``

Database snapshot transfer

SqlCipherDatabase runs synchronous SQLCipher copy and validation work on a worker task. One per-instance semaphore serializes transfers, and the UI rejects duplicate management actions while busy. A prepared import retains that reservation until install or discard; failed preparation releases it. Pre-install refusal, cancellation, or error removes only this instance's owned staging and releases the reservation. Cancellation is allowed before replacement; once replacement begins, finish the outcome and close rather than reporting an uncertain cancellation.

One private keyed-copy primitive implements development migration, export, and import. It creates a new non-pooled destination as the main database, encrypted except for an empty-password export. It then attaches the existing source through a bound, properly escaped absolute file URI with mode=ro and an explicit bound key. Development migration and plaintext imports use an empty source key. It validates and reads the source within one explicit read snapshot and invokes ``SELECT sqlcipher_export('main', 'source')``. This copies complete schema, tables, indexes, triggers, and data, not raw live bytes or selected JSON records.

The primitive preserves user_version, application_id, auto_vacuum, and sqlite_sequence high-water marks, including deleted-high-ID cases. It sets auto_vacuum before populating the destination and explicitly copies sequence contents where needed. Source schema access and source-alias integrity PRAGMAs run within the read snapshot. Plaintext sources require SQLite structural integrity but have no SQLCipher HMAC to validate; encrypted sources require both checks. Filename and ATTACH-key values are bound. A required PRAGMA literal is obtained through parameterized ``SELECT quote($value)``, not manual quoting or user-path SQL concatenation.

Temporary SQL data stays in memory. Migration outputs, import staging, and nonempty-password export outputs are encrypted throughout. Only an explicitly empty-password export uses a plaintext output and plaintext sibling temporary file. Connections are detached, checkpointed as needed, and closed. Each output is a self-contained DELETE-journal database, not a file depending on unexported WAL content. Reopening must pass schema access and integrity_check with exactly ok before success; encrypted outputs must additionally pass cipher_integrity_check with zero rows and must not have a plaintext SQLite header. Plaintext outputs are ordinary SQLite databases, with no SQLCipher header or cryptographic integrity requirement.

With a nonempty password, an export is a standalone SQLCipher 4 database protected only by the exact user-supplied export password with a new salt. With an exactly empty password, it is an ordinary unencrypted SQLite database readable without a key; this deliberate disclosure does not decrypt or otherwise change the encrypted live database or local key protector. Neither format contains a MEK wrapper, custom archive, JSON-only subset, or companion key file. Each export is written to a unique sibling of the chosen destination in its selected format. Only after complete validation is an existing destination replaced, using file replacement rather than writing through a link. Failure or cancellation leaves an existing destination intact and removes incomplete owned output. Normal database use continues during export; the read snapshot defines one consistent point in time. Files such as external photos and application logs are outside this database-only operation.

Import preparation opens the selected source read-only. An ordinary SQLite header selects plaintext handling without applying a source password; other inputs use the supplied SQLCipher password. Missing or empty files, non-databases, incorrect encryption passwords, cryptographic or structural corruption, and incompatible schema are rejected before affecting live data. Plaintext structural checks cannot authenticate the source or detect every semantically valid alteration. Compatibility is measured against all non-sqlite_% tables in the fully initialized live schema: every live table and column must exist with matching declared type, NOT NULL, and primary-key flags. Extra source tables and columns are accepted and preserved. Repository auto-migrations are not run against the source, and imported treatment loaded-state values are not reset.

An accepted import snapshot is re-encrypted into a unique staging file under StorageRoot with the existing local MEK. It preserves users, roles, settings, clinical and system histories, IDs, parent relationships, and treatment states. Neither heracles.db.key nor the locally displayed recovery key changes. Installation accepts only a validated staging path produced by this SqlCipherDatabase instance. Discard deletes only an owned staging file, never a selected source.

For both transfer directions, reject selected paths resolving to the live database, development source, key blob, any of their sidecars, or the instance's staging files. Normalize Windows paths case-insensitively and reject reparse-point aliases into protected locations. A selected import source is never deleted.

Exclusive replacement and shutdown

The host's internal DatabaseMaintenanceGate and gRPC interceptor track whole admitted unary RPCs, including error paths, under a lock; ordinary calls remain concurrent. Starting maintenance atomically rejects new unary calls with Unavailable and waits asynchronously for admitted calls to finish, including multi-connection operations. Newly starting streams are rejected during maintenance; existing streams are not part of the unary drain and are cancelled or disconnected during host shutdown. No unauthenticated database-management RPC is exposed.

After preparing staging, import obtains a unary pause/drain lease with a linked 30-second timeout. Timeout or cancellation restores admission, discards staging, and refuses import without stopping the host. After a successful drain, authorization is checked again and the host queries its existing Plan repository directly, not through the paused channel. The exact active-treatment predicate is Pendingload, Partialpendingload, or Loaded. Any such plan, or lost authorization, refuses import, removes owned staging, and reopens admission. A racing external LoadForTreatment either finishes within an admitted RPC and is visible to this check or is rejected before mutation.

Once permitted, a modal busy surface prevents further user interaction. Import stops LoadForTreatmentEventSource and PlanEventSource, stops and disposes the host with a 30-second shutdown bound, shuts down the local gRPC channel, and releases SQLite pools. Once stopping starts, the host never resumes admission. Stop and Dispose are idempotent for subsequent application exit cleanup. Failure to finish shutdown or release handles gives no permission to replace the database.

Immediately before replacement, one final non-pooled keyed live connection checks journal mode. For WAL mode it performs wal_checkpoint(TRUNCATE) and requires a non-busy result, then switches to journal_mode=DELETE and requires success. It closes before replacement. Checkpoint or journal-mode failure preserves the original and leads to application closure, without deleting an uncheckpointed WAL. Only obsolete live sidecars whose handles are released may be removed after successful finalization; old WAL or journal content must not accompany the replacement.

Installation uses same-volume File.Replace of the validated staging over the live database after all handles and pools are released. It never deletes the live database first, falls back to plaintext, or implements a merge. Replacement failure retains the original database. This limited production-import protection is distinct from the intentionally simple development migration.

On success, show ``Database imported. The application will close. Start it again to use the imported data.`` and invoke the existing IExitingModel.ExitApplication on the dispatcher. Do not refresh or resume old in-memory models against imported data, rotate the MEK, or automatically restart the application. An error after host shutdown begins is reported and also closes the application, even if the original remains intact; next startup opens whichever complete database was retained. App.OnExit uses references to initialized objects and does not restart stopped consumers.

Operational messages distinguish cancellation, an unavailable file or location, an invalid password or unreadable/damaged database, unsafe treatment state, and replacement failure, without including secret-bearing SQLCipher diagnostics, SQL, connection strings, recovery keys, or passwords. No unintended plaintext database copy or secret-bearing audit entry is produced. Unencrypted export files, their sibling temporary files, and selected plaintext import sources contain plaintext data and require appropriate protection. Import creates no additional plaintext copy: staging and the restored operational database remain encrypted.
<<<
RELATIONS:
- TYPE: Parent
  VALUE: RQ-H10SG-55
  ROLE: Refines
- TYPE: Parent
  VALUE: RQ-H10SG-789
  ROLE: Refines
- TYPE: Parent
  VALUE: RQ-H10SG-790
  ROLE: Refines

[[/SECTION]]

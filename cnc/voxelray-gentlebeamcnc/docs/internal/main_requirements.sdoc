[DOCUMENT]
TITLE: GBSK Software Requirements Specification for Internal GUI
UID: DHF-GBSK-0005
METADATA:
  COMPONENT: heracles-internal-gui

[GRAMMAR]
IMPORT_FROM_FILE: @grammar

[[SECTION]]
TITLE: Purpose

[TEXT]
STATEMENT: >>>
The purpose of this document is to provide Software Requirements Specifications for the GBSK Internal GUI software.
<<<

[[/SECTION]]

[[SECTION]]
TITLE: Scope

[TEXT]
STATEMENT: >>>
This document describes all requirements of the GBSK Internal GUI Software.

The information in this document has been derived from the VoxelRay GBSK Product Requirements Specification.

\*The term Software applies to both Software and Firmware systems.
<<<

[[/SECTION]]

[[SECTION]]
TITLE: Abbreviations and Definitions

[TEXT]
STATEMENT: >>>
===================  =====================================
Abbreviation/Term    Definition
===================  =====================================
DB                   Data Base
GUI                  Graphic User Interface
PRS                  Product Requirements Specification
SDP                  Software Development Plan
SRS                  Software Requirements Specification
SW                   Software
===================  =====================================
<<<

[[/SECTION]]

[[SECTION]]
TITLE: Overview

[TEXT]
STATEMENT: >>>
The Internal GUI SW provides a means for the user to maintain demographic patient data, including treatment plans. It communicates with the database and flange camera stream.

The internal GUI software runs on an all-in-one touchscreen PC.
<<<

[[/SECTION]]

[[SECTION]]
TITLE: References

[TEXT]
STATEMENT: >>>
================================  ==========================================
Document ID / Reference Number    Document Title
================================  ==========================================
DHF-GBSK-0001, Rev.1              GBSK Software Development Plan (SDP)
================================  ==========================================
<<<

[[/SECTION]]

[[SECTION]]
PREFIX: RQ-H10SG-
TITLE: Requirements

[REQUIREMENT]
UID: RQ-H10SG-422
TYPE: Functional
TITLE: Load For Treatment - Resume Uncompleted Treatment
STATEMENT: >>>
The application shall allow users to load an incomplete clinical plan into the external
application and enable the operator to deliver the remaining time of its singular treatment
field.

The user action shall alert when the last treatment was incomplete and offer either the
remaining scalar emission or the complete scalar emission. The external application shall
recalculate time from the latest treatment completion status.

.. image:: _assets/RQ-H10SG-422.png
<<<

[REQUIREMENT]
UID: RQ-H10SG-54
TYPE: Functional
TITLE: Main View - System Status
STATEMENT: >>>
The application shall present the user with the current immutable system status. This
status shall include the firmware mode, communication availability, system errors, emission
parameters, battery status, energy level, and emission time while the system irradiates.
Firmware-specific values that are not supplied shall be shown as unavailable rather than
as false or zero. This information should always be visible to the user.
<<<

[REQUIREMENT]
UID: RQ-H10SG-345
TYPE: Functional
TITLE: Patient - Plan View - Auto-calculate the ICDCode
STATEMENT: >>>
The application shall have an interface presenting the operator with the ICD Code based on the Site Location and pathology.

.. image:: _assets/RQ-H10SG-345.png
<<<

[REQUIREMENT]
UID: RQ-H10SG-377
TYPE: Functional
TITLE: Patient - Visits ManagementsPatient - Visits Management
STATEMENT: >>>
The application shall create a visit entity for each simulation or treatment created for a patient per day.

If the operator creates multiple simulations/treatments on the same day (e.g. for different sites), only one Visit should be created, and all simulations should be referred to the same Visit.
<<<

[REQUIREMENT]
UID: RQ-H10SG-83
TYPE: Functional
TITLE: Patients - Edit Patient Demographic Data
STATEMENT: >>>
RQ-H10SG-83The application shall allow a user to edit all the fields of an existing patient. It should have an Edit button, which will open a view with all the patient's data, and all fields should be editable.

.. image:: _assets/RQ-H10SG-83.png
<<<

[REQUIREMENT]
UID: RQ-H10SG-82
TYPE: Functional
TITLE: Patients - Patient Search
STATEMENT: >>>
RQ-H10SG-83The application shall provide a user interface to search patients.

There shall be an input field where users can enter a patient's first, middle, or last name, DOB, MRN, or ID. This field should support partial inputs for broader search capabilities.

The search results should be highlighted.

.. image:: _assets/RQ-H10SG-82.png
<<<

[REQUIREMENT]
UID: RQ-H10SG-45
TYPE: Data
TITLE: Patients - Data Manipulation Audit Trails
STATEMENT: >>>
The application shall maintain logs of all changes made to patient data, including who made the change and when.

Explicit user views of patient records, including cached revisits, shall be audited with the user and record identifiers. Background loads, refreshes, and RPC traffic alone shall not produce user-action audit records.
<<<

[REQUIREMENT]
UID: RQ-H10SG-37
TYPE: Functional
TITLE: Patients - Patient List View - Open Patient's Clinical view
STATEMENT: >>>
The patient list shall have a control that allows users to click and open the patient's clinical view (i.e., prescriptions, plans, etc.).

.. image:: _assets/RQ-H10SG-37.png
<<<

[REQUIREMENT]
UID: RQ-H10SG-39
TYPE: Functional
TITLE: Patients - Patient List View - Customizable Columns
STATEMENT: >>>
The application shall allow users to customize which data columns are displayed in the patient list view to accommodate different needs or preferences.
<<<

[REQUIREMENT]
UID: RQ-H10SG-40
TYPE: Interface
TITLE: Patients - Patient List View - Layout
STATEMENT: >>>
The application shall provide an interface to view all patients registered.

The patient list view should display key pieces of patient information:

1. MRN - patient medical record number.
2. First name
3. Middle name
4. Last name
5. Sex
6. DOB - Date of birth
7. Last visit date

.. image:: _assets/RQ-H10SG-40.png
<<<

[REQUIREMENT]
UID: RQ-H10SG-42
TYPE: Functional
TITLE: Patients - Patient Search - Results Display
STATEMENT: >>>
The application shall display search results in a list view that includes all patient information: MRN, first, middle, and last name, Gender, DOB, and Last visit.
<<<

[REQUIREMENT]
UID: RQ-H10SG-47
TYPE: Functional
TITLE: Patients - Patient's Registration Form - Cancel Button
STATEMENT: >>>
The form should have a cancel button.

The cancel button should close the form without any action.
<<<

[REQUIREMENT]
UID: RQ-H10SG-86
TYPE: Interface
TITLE: Patients - Patient's Registration Form - Layout
STATEMENT: >>>
The application shall provide a form where users can input all necessary demographic data for new patients.

The form shall include:

- First Name
- Middle Name
- Last name
- Date of birth
- MRN/ID (SSN or other)
- Sex
- Zip

.. image:: _assets/RQ-H10SG-86.png
<<<

[REQUIREMENT]
UID: RQ-H10SG-49
TYPE: Functional
TITLE: Patients - Patient's Registration Form - Patient Already Exist Error
STATEMENT: >>>
The application shall display an error message if the patient already exists.

The patient's first + last name, DOB, MRN should be unique.
<<<

[REQUIREMENT]
UID: RQ-H10SG-48
TYPE: Functional
TITLE: Patients - Patient's Registration Form - Save button
STATEMENT: >>>
The form should have a save button that adds the registered patient to the database.

The application should close the form if the save button is clicked.

The save button should be disabled if not all mandatory information is entered.
<<<

[REQUIREMENT]
UID: RQ-H10SG-50
TYPE: Functional
TITLE: Patients - Patients Registration Feedback
STATEMENT: >>>
The application shall provide immediate visual feedback for registration action.

The new user should be immediately visible in the list of user actions.
<<<

[REQUIREMENT]
UID: RQ-H10SG-52
TYPE: Functional
TITLE: Patients - Patients Registration Form - Input Data Integrity
STATEMENT: >>>
The form shall ensure data integrity by using dedicated controls for different input data types and validation rules when dedicated controls are not applicable.

Dedicated controls are:

- Date of birth - DateTime control
- ID/MRN - (SSN or other) - Numbers only input control
- Sex - drop-down list

.. image:: _assets/RQ-H10SG-52.png
<<<

[REQUIREMENT]
UID: RQ-H10SG-51
TYPE: Functional
TITLE: Patients - Patients Registration Form - Mandatory Fields
STATEMENT: >>>
The form should clearly distinguish which fields are mandatory and which are optional.

Mandatory fields should be marked with an asterisk.

[These fields are mandatory because they determine the identification of the user] Mandatory fields are:

- First Name
- Last name
- Date of birth
- Sex
- MRN
<<<

[REQUIREMENT]
UID: RQ-H10SG-187
TYPE: Safety
TITLE: Patients - Plan View - Disable any application functionality during emission
STATEMENT: >>>
The application shall prevent the user from any functionality when treatment (based on a plan) is being delivered.

The application should be triggered for a plan being delivered and shall freeze the whole user interface.

The plan will be set to a dedicated state (Loaded state), and the application shall be frozen when it is in that state.
<<<

[REQUIREMENT]
UID: RQ-H10SG-231
TYPE: Functional
TITLE: Patients - Plan View - Actual Dose Calculation
STATEMENT: >>>
A treatment plan shall be set with Energy, Duration, current, and Actual Dose.

The Actual Dose should be auto-calculate from the duration using the following function:

[Dose Rate cGy/min] \* Duration / 60

320 \* 18 / 60 = 96 cGy
<<<

[REQUIREMENT]
UID: RQ-H10SG-80
TYPE: Functional
TITLE: Patients - Plan View - Add Patient's Prescription
STATEMENT: >>>
The application shall provide a user interface that enables users to add a record of the patient's prescription for the treatment plan. The prescription data entry shall include the following fields:

1. Energy - A dropdown control for the energy Enum
2. Dose Per Fx[cGy]: An editable field accepting a decimal number.
3. Fx per week - A dropdown control for 1-7
4. TDF: A dropdown control for the TDF Enum
5. Number of Fx: An editable field accepting an integer number.
6. Total Dose [cGy]: A non-editable field whose value is automatically calculated as the product of the Dose Per Fx and the [Dose Per Fx] \* [Number of Fx].
7. Duration - The duration of the treatment
8. Add Button - Creates new prescription. When clicked, all fields shall be cleared, enabling the user to enter the data to be created and save them with the save button.
<<<

[REQUIREMENT]
UID: RQ-H10SG-193
TYPE: Functional
TITLE: Patients - Plan View - Alert for an Invalid Plan when Editing Energy in a Prescription
STATEMENT: >>>
The application shall alert the user of an invalid plan if the Energy level of a prescription is edited.

The duration of the treatment is calculated based on the Energy level of the prescription. If The Energy is edited, the calculation is not valid. The application should alert the user.
<<<

[REQUIREMENT]
UID: RQ-H10SG-382
TYPE: Functional
TITLE: Patients - Plan View - Alert for unsaved data
STATEMENT: >>>
The user shall be alerted to unsaved data when exiting the plan view (e.g., pressing the scan or capture buttons, which opens a different view) without saving edited data.

.. image:: _assets/RQ-H10SG-382.png
<<<

[REQUIREMENT]
UID: RQ-H10SG-740
TYPE: Functional
TITLE: Patients - Plan View - Auto-Calculation Field Size
STATEMENT: >>>
When adding/editing a simulation, the application shall automatically calculate the Field Size based on the set Lesion size and Margin size.

The calculation shall use the following method:

Field Size X [cm] = Lesion Size X + 2 \* Margin Size X [cm]

Field Size Y [cm] = Lesion Size Y + 2 \* Margin Size Y [cm]

For example:

Lesion Size = 1.0 x 1.0

Margin Size = 0.5 x 0.5

Field Size = 2.0 x 2.0

.. image:: _assets/RQ-H10SG-740.png
<<<

[REQUIREMENT]
UID: RQ-H10SG-739
TYPE: Functional
TITLE: Patients - Plan View - Auto-Calculation of Emission Duration
STATEMENT: >>>
When adding a new prescription, the application shall automatically calculate the suggested emission Duration based on the prescribed dose and the used applicator's dose rate.

The application shall calculate emission duration with a minimum resolution of 0.1 seconds.

The calculation will use the following method:
Duration [sec] = Prescribed Dose [cGy] / Dose Rate [cGy/min] \* 60
<<<

[REQUIREMENT]
UID: RQ-H10SG-738
TYPE: Functional
TITLE: Patients - Plan View - Auto-Calculation of Energy level and TDF of New Prescription
STATEMENT: >>>
When adding a new prescription, the application shall automatically calculate the suggested Energy Level, Total Number of Fractions, Fraction per Week, and TDF values based on the input parameters of Pathology of the field, Lesion Size, and Cell Type set in the simulation and a predefined clinical protocol.

The application shall enable the user to edit this suggestion.

The used protocol: GentleCure Protocol _ Final April 2025.pdf
<<<

[REQUIREMENT]
UID: RQ-H10SG-332
TYPE: Functional
TITLE: Patients - Plan View - Automatically Identify Connected Collimator
STATEMENT: >>>
The application shall be able to query the type of connected collimator and its supported energy and SSD.
<<<

[REQUIREMENT]
UID: RQ-H10SG-89
TYPE: Functional
TITLE: Patients - Plan View - Create Patient's Treatment Simulation
STATEMENT: >>>
The application shall provide a user interface that enables users to add a record of the patient's treatment simulation. The simulation data entries shall include the following fields:

1. Lesion Size[cm2] - Two edit boxes (numbers) for the two dimensions value.
2. Margin Size[cm2] - Number edit box.
3. Shield Size[cm] - Number edit box.
4. Lesion Depth[mm] - Number edit box
5. Position - A list selected from a dropdown menu.
6. Devices - A list selected from a dropdown menu.
7. Notes - Edit box
<<<

[REQUIREMENT]
UID: RQ-H10SG-14
TYPE: Safety
TITLE: Patients - Plan View - Disable Treatment when the Patient's Plan is Inconsistent
STATEMENT: >>>
The application shall not enable treatment delivery if the plan's applicator type differs from the actual applicator type.

The application shall present an error message when the user tries to load the plan into the external application (i.e. presses the LoadForTreatemt).
<<<

[REQUIREMENT]
UID: RQ-H10SG-23
TYPE: Functional
TITLE: Patients - Plan View - Edit Patient's Prescription
STATEMENT: >>>
The application shall provide an interface to enable users to edit the patient's prescription. A prescription will not be editable if it is approved.
<<<

[REQUIREMENT]
UID: RQ-H10SG-232
TYPE: Functional
TITLE: Patients - Plan View - Emission Current Calculation
STATEMENT: >>>
A treatment plan shall be set with Energy, Duration, Current, and Actual Dose.

The Current should be auto calculated as the quotient of Power[W] divided by Energy Level[kV]:

Emission Current[mA] = Power[W] / Voltage[kV]

The device shall operate at a constant power of 50W.

Here are the calculated values as a dependency on Energy Level:

========  ===========  =====================
Power[W]  Voltage[kV]  Emission Current[mA]
========  ===========  =====================
50        50           1
50        70           0.71
50        100          0.5
========  ===========  =====================
<<<

[REQUIREMENT]
UID: RQ-H10SG-81
TYPE: Interface
TITLE: Patients - Plan View - Layout
STATEMENT: >>>
The application shall provide a user interface to enable users to manage patients' clinical data.

The view will include:

1. The patient demographic data section for the identification of the user
2. The Sites list
3. Simulation Details:

   - Lesion size[cm2] - Two edit boxes (numbers) for the two dimensions value
   - Lesion Depth[mm] - Number edit box.
   - Margin Size[cm2] - Two edit boxes (numbers) for the two dimensions value
   - Field Size [cm2] - A calculated field based on Lesion Size and Margin Size
   - Position - A list selected from a dropdown menu.
   - Device - A list selected from a dropdown menu.
   - Notes - Edit box

4. Prescription - The latest approved prescription (if exists) or the latest prescription exists.

   - Dose Per Fx[cGy] - Decimal edit box
   - Fx per week - Number Edit box.
   - Number of Fx - Number Edit box.
   - TDF - Dropdown control
   - Energy[kV]
   - Total Dose[cGy] - calculated field [Dose Per Fx] \* [Number of Fx]
   - Duration
   - Actual Dose

5. Treatment history


   - The UI Layout shall be implemented as a master-detail view within a multi-tab control.

The master view shall present a list of the sites, and the details view shall present the clinical data
(simulation, prescription, and plan details).

.. image:: _assets/RQ-H10SG-81.png
<<<

[REQUIREMENT]
UID: RQ-H10SG-184
TYPE: Functional
TITLE: Patients - Plan View - Load For Treatment
STATEMENT: >>>
The application shall have a user interface that allows users to load the plan into the external application and enable the user to activate the patient's treatment.

The user shall have an action button that sends the plan to the external application. Once this action is accepted, the plan shall be visible in the external application.

An accepted load shall be made available consistently to every connected client.

Before a plan is accepted for loading, the application shall require exactly one valid
treatment field. A missing, additional, or invalid field shall be rejected.
<<<

[REQUIREMENT]
UID: RQ-H10SG-186
TYPE: Functional
TITLE: Patients - Plan View - Load For Treatment - Cancelation
STATEMENT: >>>
The application shall have an interface that allows the user to cancel a plan loading and to enable the user to review the plan. This shall only be allowed if the plan delivery process has not started.
<<<

[REQUIREMENT]
UID: RQ-H10SG-15
TYPE: Safety
TITLE: Patients - Plan View - Patient's Plan Inconsistency Alert
STATEMENT: >>>
The application shall alert the user if there is an inconsistency between the planned applicator Type and the actual connected applicator.
<<<

[REQUIREMENT]
UID: RQ-H10SG-16
TYPE: Functional
TITLE: Patients - Plan View - Patient's Treatment Plan Audit Trial
STATEMENT: >>>
The application shall log explicit user actions on the treatment plan, including viewing records, creating or updating the simulation or prescription, and approving the plan. The audit shall identify who performed the action and when, distinguish requested actions from successful changes, and exclude automatic refreshes and background RPC activity.
<<<

[REQUIREMENT]
UID: RQ-H10SG-162
TYPE: Safety
TITLE: Patients - Plan View - Plan's Treatment Parameters Validation in case of Applicator's Dose Rate Changes
STATEMENT: >>>
The application shall validate the treatment parameters fetched from the DB, including duration and dose, and alert the user if they are inconsistent with the calculated parameters.

The duration and dose of a treatment are calculated based on the calibrated Dose Rate. The application should recalculate these parameters and compare them with those fetched from the DB.
<<<

[REQUIREMENT]
UID: RQ-H10SG-191
TYPE: Functional
TITLE: Patients - Plan View - Prevent editing of approved patient's prescription
STATEMENT: >>>
The application should disallow users from editing a prescription of an approved plan. The edit box should be disabled.
<<<

[REQUIREMENT]
UID: RQ-H10SG-331
TYPE: Functional
TITLE: Patients - Plan View - Setting Energy Level
STATEMENT: >>>
The application shall provide the user with an interface for setting the energy level of the patient's plan.

A treatment plan shall be set with Energy, Duration, current, and Actual Dose.
<<<

[REQUIREMENT]
UID: RQ-H10SG-17
TYPE: Functional
TITLE: Patients - Plan View - Verify Patient's Treatment Plan
STATEMENT: >>>
The application shall allow users to approve/verify the treatment Plan.

Approving a plan should trigger a pop-up asking the user for his user, password, and status to transit the plan.

The status shall be one of the following:

Name                 | UI Label
PlanApproved         | Approved
Rejected             | Rejected
<<<

[REQUIREMENT]
UID: RQ-H10SG-88
TYPE: Functional
TITLE: Patients - Plan View - View Patient's Treatment Simulation
STATEMENT: >>>
The application should allow the user to view the patient's treatment simulation.

The Simulation view should include the following measures:
1. Lesion size[cm2] - Two edit boxes (numbers) for the two dimensions value
2. Lesion Depth[mm] - Number edit box.
3. Margin Size[cm2] - Two edit boxes (numbers) for the two dimensions value
4. Field Size [cm2] - A calculated field based on Lesion Size and Margin Size
5. Position - A list selected from a dropdown menu.
6. Device - A list selected from a dropdown menu.
7. Notes - Edit box
<<<

[REQUIREMENT]
UID: RQ-H10SG-185
TYPE: Functional
TITLE: Patients - Plan View- Load For Treatment - Disallow Plan Editing
STATEMENT: >>>
The application shall disallow any change in the plan when the plan is sent to the external application.

When the user triggers the Load for Treatment action, a modal pop-up will be displayed, disabling the user from editing the plan. The Plan status will be changed to Pending.
<<<

[REQUIREMENT]
UID: RQ-H10SG-388
TYPE: Functional
TITLE: Patients - Plan view - Create Site (Field)
STATEMENT: >>>
The application shall provide a user interface that enables users to add a record of the patient's site (field). The site data entry shall include the following fields:

1. Field Name - Edit box for the field name
2. Site Location - A Dropdown control for selecting the location.
3. Pathology - A Dropdown control for selecting the pathology
4. Subcell - A Dropdown control for selecting the Subcell. The display list is dependent on the selected pathology
5. Description - A Dropdown control for selecting pathology description
6. Referring provider. - The Referring doctor.

.. image:: _assets/RQ-H10SG-388.png
<<<

[REQUIREMENT]
UID: RQ-H10SG-385
TYPE: Functional
TITLE: Patients - Plan view - Create Site (Field) - Pathology
STATEMENT: >>>
The application shall provide a dropdown control that enables users to select Pathology when creating a new site (field), which can be one of the following Enum:

=================== ======== ========================
Name                Number   Description (UI Label)
=================== ======== ========================
UNSPECIFIED         0
BCC                 1        BCC
SCC                 2        SCC
SCC-IS              3        SCC-IS
Keloid              4        Keloid
Basosquamous        5        Basosquamous
=================== ======== ========================
<<<

[REQUIREMENT]
UID: RQ-H10SG-389
TYPE: Functional
TITLE: Patients - Plan view - Create Site (Field) - Pathology Description
STATEMENT: >>>
The application shall provide a dropdown control that enables users to select the Pathology Description of the field created. Description when creating a new site (field), which can be one of the following Enum:

================================== ======== =================================
Name                               Number   Description (UI Label)
================================== ======== =================================
UNSPECIFIED                        0
Infundibulo_cytic                  1        Infundibulo-cytic
Ulcerated_long_standing            2        Ulcerated long-standing
Adenosquamous                      3        Adenosquamous
Desmoplastic_Metaplastic           4        Desmoplastic/Metaplastic
Recurrent_Lesion_post_surgery      5        Recurrent Lesion post-surgery
Large_Lesion                       6        Large Lesion
Deep_Lesion                        7        Deep Lesion
Rapid_growth                       8        Rapid growth
Extension_into_hair_follicle       9        Extension into hair follicle
================================== ======== =================================
<<<

[REQUIREMENT]
UID: RQ-H10SG-384
TYPE: Functional
TITLE: Patients - Plan view - Create Site (Field) - Site Location
STATEMENT: >>>
The application shall provide a dropdown control that enables users to select the location of the field (site) when creating a new field, which can be one of the following Enum:

=================== ======== ===================
Name                Number   Description (UI)
=================== ======== ===================
UNSPECIFIED         0
Breast              1        Breast
LeftEar             2        Ear (Left)
RightEar            3        Ear (Right)
Forehead            4        Forehead
Temple              5        Temple
Zygoma              6        Zygoma
PreAuricular        7        Pre-Auricular
Cheek               8        Cheek
Chin                9        Chin
Jaw                 10       Jaw
Lip                 11       Lip
Neck                12       Neck
Nose                13       Nose
Scalp               14       Scalp
PostAuricular       15       Post Auricular
Trunk               16       Trunk
Chest               17       Chest
Abdomen             18       Abdomen
Back                19       Back
LeftLowerLimb       20       Lower Limb (Left)
RightLowerLimb      21       Lower Limb (Right)
LeftUpperLimb       22       Upper Limb (Left)
RightUpperLimb      23       Upper Limb (Right)
RightUpperEyelid    24       Eyelid (Right Upper)
RightLowerEyelid    25       Eyelid (Right Lower)
LeftUpperEyelid     26       Eyelid (Left Upper)
LeftLowerEyelid     27       Eyelid (Left Lower)
=================== ======== ===================
<<<

[REQUIREMENT]
UID: RQ-H10SG-386
TYPE: Functional
TITLE: Patients - Plan view - Create Site (Field) - Subcell
STATEMENT: >>>
The application shall provide a dropdown control that enables users to select the subcell when creating a new site (field).

The dropdown will show a list of possible subcells depending on the selected Pathology as follows: if there are no corresponding subtypes, the dropdown should be disabled.

**Basal Cell Carcinoma**

Subtypes: Aberrant, Adenoid, Atypical Basaloid Proliferation, Basosquamous (Metatypical), Adnexal Differentiation, Squamous Differentiation, Clear Ring, Cystic Cell Carcinoma, Fibroepithelioma of Pinkus, Infiltrative, Keratotic, Micro Nodular, Mixed Pattern, Morphoeic/Sclerosing/Fibrosing, Nodular (Classic Basal-Cell), Nodulocystic, Pigmented, Pleomorphic, Polypoid, Pore-like, Rodent Ulcer (Jacobi Ulcer), Superficial (Multicentric), Other

**Squamous Cell Carcinoma**

Subtypes: Acantholytic, Adenoid/Pseudoglandular, Atypical Squamous Proliferation, Basaloid, Clear-cell, Erythroplasia, Intraepidermal, Invasive, Keratoacanthoma, Large Cell Keratinizing, Large Cell Non-Keratinizing, Metaplasia, Mixed Pattern, Moderately Differentiated, Poorly differentiated, Papillary Carcinoma, Signet-ring cell, Small Cell Keratinizing, Superficial, Spindle Cell, Verrucous, Well-Differentiated, Superficially Invasive, Other

**Basosquamous Cell Carcinoma**

Subtypes: No Subtypes

**Keloid**

Subtypes: No Subtypes

**Squamous Cell Carcinoma In-Situ**

Subtypes: No Subtypes
<<<

[REQUIREMENT]
UID: RQ-H10SG-192
TYPE: Functional
TITLE: Patients - Plan view - Prevent Updating Approved Plan
STATEMENT: >>>
The application shall prevent users from editing an approved plan. The edit box should be disabled.
<<<

[REQUIREMENT]
UID: RQ-H10SG-24
TYPE: Functional
TITLE: Patients - Plan view - view patient's prescription
STATEMENT: >>>
The application shall provide a user interface for the user to view the patient's prescription.

The prescription displayed should be the one created for the selected simulation.

.. image:: _assets/RQ-H10SG-24.png
<<<

[REQUIREMENT]
UID: RQ-H10SG-95
TYPE: Functional
TITLE: Patients - Treatment View - View Treatment Details
STATEMENT: >>>
The application shall have an interface that enables the user to observe the patient's treatment delivered and their corresponding parameters.

The treatment fields shall be a collapse-expand-like view and should be visible when the user presses the Details button of the selected treatment

The treatment data should include the following information:

- Actual duration - The actual duration of the delivery of emissions.
- Actual Dose - The actual dose delivered in this field.
- The current - the emission current.
<<<

[REQUIREMENT]
UID: RQ-H10SG-94
TYPE: Functional
TITLE: Patients - Treatments view - Layout
STATEMENT: >>>
The application shall have an interface enabling the user to observe the patient's treatment history for a certain site (field).

The layout should include the patient data at the top of the view.

The treatment history view shall be arranged as a master-details view. The master view shall include a list of sites.

The details view should include:

1. The simulation data

2. The prescription data.

3. A table listing all the treatments delivered (fractions), including the following information:

===================== ======================================================================
Column Name           Description
===================== ======================================================================
FX                    The fraction number
Date                  The date of the treatment.
Lesion depth          The Lesion depth measured during that visit
Energy                The energy delivered in kV
Daily Dose            The delivered dose in cGy
Cumulative Dose       Cumulative Dose in cGy
Performed by          The user who performed this treatment
Details               A link field shall open the details of the delivered treatment.
===================== ======================================================================
<<<

[REQUIREMENT]
UID: RQ-H10SG-118
TYPE: Functional
TITLE: Physics - Alert for unsaved data
STATEMENT: >>>
The user shall be alerted to unsaved data when navigating out of the view without saving the current edited tab.
<<<

[REQUIREMENT]
UID: RQ-H10SG-110
TYPE: Functional
TITLE: Physics - Coil configuration
STATEMENT: >>>
The application shall have a user interface that allows users (role-based) to configure the target Coil parameters, which control the focus and deflection of the beam.
<<<

[REQUIREMENT]
UID: RQ-H10SG-112
TYPE: Functional
TITLE: Physics - Heater current configuration.
STATEMENT: >>>
The application shall have a user interface that allows users (role-based) to configure the DAC value for the filament-preheat level, one for each applicator type, SSD, and kV.
<<<

[REQUIREMENT]
UID: RQ-H10SG-115
TYPE: Functional
TITLE: Physics - Import configuration from CSV file
STATEMENT: >>>
The application shall have a user interface that allows users (role-based) to import physics parameters from a CSV file.

The CSV file shall include configuration for coils, magnetometer, heater current, and applicator dose rate.
<<<

[REQUIREMENT]
UID: RQ-H10SG-121
TYPE: Functional
TITLE: Physics - Import configuration from CSV file - Improper formatting in the CSV
STATEMENT: >>>
The user shall be alerted if the imported CSV has improper formatting and the import process field.
<<<

[REQUIREMENT]
UID: RQ-H10SG-120
TYPE: Functional
TITLE: Physics - Layout
STATEMENT: >>>
The application shall have a user interface that allows users (role-based) to configure the system physics data. The data shall be entered manually or as data imported from a CSV file.

The interface layout shall include:

1. File upload control enables the user to load files from the filesystem.
2. A dropdown box for the applicator type.
3. A dropdown box for the applicator Energy Level.
4. A multi-panel view for each configuration: Magnetometer, Heater Current, Coils and Dose Rate of the selected applicator

.. image:: _assets/RQ-H10SG-120.png
<<<

[REQUIREMENT]
UID: RQ-H10SG-111
TYPE: Functional
TITLE: Physics - Magnetometer correction parameters
STATEMENT: >>>
The application shall have a user interface that allows users (role-based) to configure the magnetometer correction parameters before installation for each energy level. The parameters shall be utilized to compensate for the offset effects of ambient magnetic fields on the electron beam steering.

The parameters include the Correction Matrix and the Reference Fields for the back and front magnetometers.
<<<

[REQUIREMENT]
UID: RQ-H10SG-119
TYPE: Functional
TITLE: Physics - Save Data
STATEMENT: >>>
The user shall be able to save physics data. The save button shall be disabled when no new data is to be saved or when there is an error in one of the inputs and enabled when a change is made.
<<<

[REQUIREMENT]
UID: RQ-H10SG-114
TYPE: Functional
TITLE: Physics - Set Applicator Dose-Rate
STATEMENT: >>>
The application shall have a user interface that allows users (role-based) to configure the applicator's dose rate.
<<<

[REQUIREMENT]
UID: RQ-H10SG-190
TYPE: Safety
TITLE: Quality Assurance - Quality Checks Reports
STATEMENT: >>>
The application shall provide an interface (Role-based) for users to view the history of quality checks performed in the system.

The quality checks report will be filtered by the type of applicator used for testing, its energy, SSD, and the date of the test.

The report will include a table of intensity measured in the quality check process.
<<<

[REQUIREMENT]
UID: RQ-H10SG-344
TYPE: Safety
TITLE: Quality Assurance - Quality Checks Reports - Deviation - UI
STATEMENT: >>>
The application shall provide the operator with an interface displaying the history of quality test results.

The quality checks report will be filtered by the type of collimator it was tested with, its energy, SSD, and the date it was performed.

The report shall show the current, measured intensity, and deviation from the referenced
test for each requested QA emission.
<<<

[REQUIREMENT]
UID: RQ-H10SG-55
TYPE: Cybersecurity
TITLE: Security - Data Encryption
STATEMENT: >>>
The software shall encrypt all data in its operational database at rest with an encryption strength of at least 128 bits.
<<<

[REQUIREMENT]
UID: RQ-H10SG-789
TYPE: Cybersecurity
TITLE: Security - Database Integrity
STATEMENT: >>>
The software shall protect the integrity of its operational database through cryptographic means.
<<<

[REQUIREMENT]
UID: RQ-H10SG-790
TYPE: Functional
TITLE: Data Recovery and Backup
STATEMENT: >>>
The software shall allow administrators to recover access to stored data and to export and restore the database using password-protected backups, and to explicitly choose an unencrypted database export.
<<<

[REQUIREMENT]
UID: RQ-H10SG-65
TYPE: Functional
TITLE: Service - System's Signals
STATEMENT: >>>
The application shall have a user interface allowing the service engineer to view semantic
real-time system signals decoded from the board telemetry according to the reported
firmware mode.

The System Signals to be presented are:

+--------------------+-------------------------+-------+
| Type               | Field                   | Unit  |
+====================+=========================+=======+
| Coils              | Y coil current          | [mA]  |
+--------------------+-------------------------+-------+
| Coils              | X coil current          | [mA]  |
+--------------------+-------------------------+-------+
| Coils              | Focus current           | [mA]  |
+--------------------+-------------------------+-------+
| Ion Pump           | Ion pump voltage        | [V]   |
+--------------------+-------------------------+-------+
| Magnetometer       | Mag 1 X                 | [µT]  |
+--------------------+-------------------------+-------+
| Magnetometer       | Mag 1 Y                 | [µT]  |
+--------------------+-------------------------+-------+
| Magnetometer       | Mag 1 Z                 | [µT]  |
+--------------------+-------------------------+-------+
| Magnetometer       | Mag 2 X                 | [µT]  |
+--------------------+-------------------------+-------+
| Magnetometer       | Mag 2 Y                 | [µT]  |
+--------------------+-------------------------+-------+
| Magnetometer       | Mag 2 Z                 | [µT]  |
+--------------------+-------------------------+-------+
| Cooling system     | Water pressure          | [psi] |
+--------------------+-------------------------+-------+
| Cooling system     | Water Flow              | [lpm] |
+--------------------+-------------------------+-------+
| Cooling system     | Water temperature       | [˚ C] |
+--------------------+-------------------------+-------+
| Cooling system     | HeadSink temperature    | [˚ C] |
+--------------------+-------------------------+-------+
| Cooling system     | Peltier temperature     | [˚ C] |
+--------------------+-------------------------+-------+
| Cooling system     | Cabinet temperature     | [˚ C] |
+--------------------+-------------------------+-------+
| HVPS               | HVPS Runtime            | [ms]  |
+--------------------+-------------------------+-------+
| HVPS               | HVPS IO                 | [Raw] |
+--------------------+-------------------------+-------+
| HVPS               | HVPS Status Flags       | [Raw] |
+--------------------+-------------------------+-------+
| HVPS               | kV Feedback             | [kV]  |
+--------------------+-------------------------+-------+
| HVPS               | Filament setpoint       | [mA]  |
+--------------------+-------------------------+-------+
| HVPS               | Filament feedback       | [mA]  |
+--------------------+-------------------------+-------+
| HVPS               | Grid feedback           | [V]   |
+--------------------+-------------------------+-------+
| HVPS               | Grid setpoint           | [V]   |
+--------------------+-------------------------+-------+
| System             | Firmware mode           |       |
+--------------------+-------------------------+-------+
| System             | System state            |       |
+--------------------+-------------------------+-------+
| System             | System runtime          | [ms]  |
+--------------------+-------------------------+-------+
| System             | Fault category flags    |       |
+--------------------+-------------------------+-------+
| System             | Interlock states        |       |
+--------------------+-------------------------+-------+
| System             | Raw interlock flags     | [Raw] |
+--------------------+-------------------------+-------+
| System             | Required interlocks     | [Raw] |
+--------------------+-------------------------+-------+
| General            | Ring LED State          |       |
+--------------------+-------------------------+-------+
| General            | Base LED State          |       |
+--------------------+-------------------------+-------+
| General            | Applicator ID (1)       | [Raw] |
+--------------------+-------------------------+-------+
| General            | Applicator ID (2) [Raw] | [Raw] |
+--------------------+-------------------------+-------+
| General            | Buttons                 | [Raw] |
+--------------------+-------------------------+-------+
| Timers             | Internal Timer State    |       |
+--------------------+-------------------------+-------+
| Timers             | Internal Timer Value    | [sec] |
+--------------------+-------------------------+-------+
| Timers             | Timer 1 State           |       |
+--------------------+-------------------------+-------+
| Timers             | Timer 1 Value           | [sec] |
+--------------------+-------------------------+-------+
| Timers             | Timer 2 State           |       |
+--------------------+-------------------------+-------+
| Timers             | Timer 2 Value           | [sec] |
+--------------------+-------------------------+-------+

The service interface shall display the signals supported by the reported firmware mode
and the current latched fault information.

.. image:: _assets/RQ-H10SG-65.png
<<<

[REQUIREMENT]
UID: RQ-H10SG-619
TYPE: Cybersecurity
TITLE: Settings - Users Authorization Management - Create New Role
STATEMENT: >>>
The application shall provide an authorized user the ability to add new roles to the system and assign specific permissions to these roles.

.. image:: _assets/RQ-H10SG-619.png
<<<

[REQUIREMENT]
UID: RQ-H10SG-618
TYPE: Cybersecurity
TITLE: Settings - Users Authorization Management - Set/Unset Permissions
STATEMENT: >>>
The application shall provide a super user the ability to manage the users' access permissions.

The user will be able to set or unset the permissions to the predefined roles: RTT, Physicist, Service, and Administrator.

**With the following permissions:**

Patient's Clinical Data, Patient's Treatment, System Calibration, Quality Assurance, System Settings, User Management, and Services

.. image:: _assets/RQ-H10SG-618.png
<<<

[REQUIREMENT]
UID: RQ-H10SG-128
TYPE: Functional
TITLE: System Setting View - Applicator Management - Deactivate Applicator
STATEMENT: >>>
The application shall have a user interface that allows users (role-based) to deactivate an applicator in case it is not used by the system (e.g. if it is out of order).

The user shall select the deactivated applicator and, in the edit view, will deselect the Active parameters.
<<<

[REQUIREMENT]
UID: RQ-H10SG-127
TYPE: Functional
TITLE: System Setting View - Applicator Management - Register New Applicator
STATEMENT: >>>
The application shall have a user interface that allows users (role-based) to register new applicators.

The user will register an applicator when it is connected to the head.

The applicator serial will be identified automatically by the firmware, and the user will enter all other parameters:

1. Type - The applicator type (Target Type) will be displayed as a dropdown control listing the supported applicator types.
2. Energy - The applicator supported energy - A drop-down control that lists all support energy levels.
3. SSD - The collimator source to skin distance. [30,50] (optional)
4. Active - The collimator will be created active by default.

.. image:: _assets/RQ-H10SG-127.png
<<<

[REQUIREMENT]
UID: RQ-H10SG-126
TYPE: Functional
TITLE: System Setting View - Applicators Management - Layout
STATEMENT: >>>
The application shall have a user interface that allows users (role-based) to manage the system applicators. The user shall be able to view the currently registered applicators, add a new applicator definition, edit the data of an existing one, and deactivate an applicator if it is no longer in use.

.. image:: _assets/RQ-H10SG-126.png
<<<

[REQUIREMENT]
UID: RQ-H10SG-321
TYPE: Functional
TITLE: System Setting View - Applicators Management - New Applicators Mandatory Fields
STATEMENT: >>>
The New Applicators form should clearly distinguish which fields are mandatory and which are optional.

Mandatory fields should be marked with an asterisk.

Mandatory fields are:

- Serial
- Type
- Energy
- SSD

.. image:: _assets/RQ-H10SG-321.png
<<<

[REQUIREMENT]
UID: RQ-H10SG-383
TYPE: Functional
TITLE: System Setting View - Collimators Management - Register QC Collimator
STATEMENT: >>>
The application shall have a user interface that allows users (role-based) to register the QC dedicated collimator.

The user will register the collimator when it is connected to the head.

The collimator serial will be identified automatically by the firmware, and the user will enter all other parameters:

1. Type - The TARGET_TYPE_QC_COLLIMATOR type will be selected.
2. Energy - will be automatically set to 50.
3. SSD - will be automatically set to 50.
4. Active - The collimator will be created active by default.
<<<

[REQUIREMENT]
UID: RQ-H10SG-249
TYPE: Functional
TITLE: System Setting View - Device Serial ID
STATEMENT: >>>
The application shall have an interface (pop-up) allowing the user to enter the device serial ID.

The pop-up should be visible when the application is started, and no device ID is defined.

The Device ID should be saved to the database. The cloud application will use it to identify the device from which the data is synced.

.. image:: _assets/RQ-H10SG-249.png
<<<

[REQUIREMENT]
UID: RQ-H10SG-124
TYPE: Functional
TITLE: System Setting View - Endpoint configuration
STATEMENT: >>>
The application shall have a user interface that allows users (role-based) to configure the system endpoints to enable communication between system components.

Committed user changes to endpoint configuration shall be audited with the acting user and affected configuration identifiers. Editing, cancelling, failed saves, and background reads shall not be recorded as successful configuration changes.

.. image:: _assets/RQ-H10SG-124.png
<<<

[REQUIREMENT]
UID: RQ-H10SG-125
TYPE: Cybersecurity
TITLE: System Setting View - User Managements
STATEMENT: >>>
The application shall have a user interface that allows admin users to manage the system users.

The admin should be able to add, edit, or delete users.

Settings > User Management shall display account lock status and offer Reset lockout for a selected account with at least 10 failed login attempts. Only an authenticated Administrator with an active, unlocked, unexpired session may enable the confirmed action.

The server shall independently authorize the bearer session against its current persisted user and exact built-in Administrator role. Missing or forged sessions and non-administrator, deleted, demoted, or locked actors shall be rejected. A successful reset shall persist only the target's failed-login count as zero, preserving credentials, last access, and other account data, and shall atomically record the actor and target identifiers in the security audit. Audit persistence failure shall roll back the reset. A target below the lockout threshold shall remain unchanged without a reset-success audit. Ordinary user editing shall not change the output-only failed-login count.

.. image:: _assets/RQ-H10SG-125.png
<<<

[REQUIREMENT]
UID: RQ-H10SG-67
TYPE: Functional
TITLE: System logs' view - Layout
STATEMENT: >>>
The application should have a user interface allowing users to view system logs.

The user interface should include:

1. An edit control for the term of the search.
2. A calendar control for selecting the time frame of the log.
3. A filter link button that will trigger the opening of the filter selection.
4. A search button to trigger the search.
5. A list view for the search result
<<<

[REQUIREMENT]
UID: RQ-H10SG-74
TYPE: Cybersecurity
TITLE: User Authentication
STATEMENT: >>>
The application shall have a user interface allowing users to input credentials and be authenticated by the system.

Once the user is logged in, the application should hold the authentication token and use it for all the API requests.

Login outcomes shall be persisted in the security log without credentials or bearer tokens; failure to persist the outcome shall fail closed and shall not create an authenticated session. Failed passwords for an existing unlocked account shall increment its persisted failed-login count; at 10 failures the account shall remain locked across application or server restart, including when the correct password is supplied. Successful login below 10 failures shall reset the count to zero.

Approval credential checks shall reject locked accounts without changing their failed-login count on either valid or invalid credentials. An Administrator may reset a locked account through the dedicated User Management action; reset does not authenticate the target user.
<<<

[REQUIREMENT]
UID: RQ-H10SG-648
TYPE: Cybersecurity
TITLE: User Login - Show/Hide Password
STATEMENT: >>>
The application shall have a control that allows the user to view or hide the typed password on the login page.

Default view - The password is hidden.

.. image:: _assets/RQ-H10SG-648-1.png

When clicking on the icon - The password is shown.

.. image:: _assets/RQ-H10SG-648-2.png
<<<

[REQUIREMENT]
UID: RQ-H10SG-68
TYPE: Functional
TITLE: User Profile Management
STATEMENT: >>>
The application should have a user interface to enable a super user to view, assign, and update user's roles.
<<<

[REQUIREMENT]
UID: RQ-H10SG-741
TYPE: Safety
TITLE: Disable Patient Functions in Calibration Mode
STATEMENT: >>>
When the connected control board reports calibration firmware mode, the indoor application
shall disable the Patients tab and obscure its content with a message directing the user to
service the device. Non-patient service functions shall remain accessible.
<<<

[[/SECTION]]

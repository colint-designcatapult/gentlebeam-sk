[DOCUMENT]
TITLE: GBSK UCSI Software Design Specification
UID: DHF-GBSK-UCSI-0002
METADATA:
  COMPONENT: heracles-ucsi

[GRAMMAR]
IMPORT_FROM_FILE: @grammar

[[SECTION]]
TITLE: Purpose

[TEXT]
STATEMENT: >>>
This document describes the architectural design of the GBSK UCSI service interface.
<<<

[[/SECTION]]

[[SECTION]]
TITLE: Scope

[TEXT]
STATEMENT: >>>
This document describes the UCSI application and module architecture that implements the UCSI Software Requirements Specification, DHF-GBSK-UCSI-0001.
<<<

[[/SECTION]]

[[SECTION]]
TITLE: Abbreviations and Definitions

[TEXT]
STATEMENT: >>>
===================  ==========================================
Abbreviation/Term    Definition
===================  ==========================================
GCB                  Gryphon Control Board
HVPS                 High Voltage Power Supply
MVVM                 Model-View-ViewModel
UCSI                 GBSK technician-facing service interface
===================  ==========================================
<<<

[[/SECTION]]

[[SECTION]]
TITLE: Architecture Overview

[TEXT]
STATEMENT: >>>
The UCSI user interface is implemented as WPF views bound to an MVVM view model. The same view model and service registrations are used by the standalone application and by the UCSI module hosted in the GBSK system PC software. Telemetry and command services connect the interface to the control-board and HVPS communication channels.
<<<

[[/SECTION]]

[[SECTION]]
PREFIX: SDS-UCSI-
TITLE: Design Items

[DESIGN_ITEM]
UID: SDS-UCSI-001
TITLE: Shared UCSI composition
STATEMENT: >>>
The UcsiRegistration composition root registers the UCSI views, view model, telemetry services, storage services, and command interfaces. The standalone application creates this composition directly; the UcsiModule exposes the same registration for the hosted system-PC application.
<<<
RELATIONS:
- TYPE: Parent
  VALUE: RQ-UCSI-001
  ROLE: Refines

[DESIGN_ITEM]
UID: SDS-UCSI-002
TITLE: Telemetry status presentation
STATEMENT: >>>
TelemetrySessionCoordinator receives system telemetry and makes the current sample available to the UCSI view model. The view model maps the sample into the system-status, interlock, HVPS-state, fault, and monitored-parameter views through the telemetry parameter catalog. The UCSI log buffer supplies operational log entries to the view model, which saves the displayed entries to a timestamped text file on operator request.
<<<
RELATIONS:
- TYPE: Parent
  VALUE: RQ-UCSI-002
  ROLE: Refines

[DESIGN_ITEM]
UID: SDS-UCSI-003
TITLE: Telemetry monitoring and session data
STATEMENT: >>>
TelemetryHistoryBuffer retains received live samples with their UTC timestamps for display and recent-history selection. The operator selects parameters from TelemetryParameterCatalog for the monitored-parameter list and graph panes. TelemetrySessionCoordinator records and reads telemetry sessions through the Parquet session storage services and controls replay play, pause, seek, and return-to-live transitions.

On operator request, SessionDataExportService writes only samples received during the preceding five minutes to CSV. FaultTelemetryExportService runs in both deployment modes and tracks the active set reported by FaultsChangedEvent. For each newly active fault, it snapshots the preceding five minutes once and queues a separate fault-tagged CSV export. Repeated updates for a fault that remains active do not create another export; a fault that clears and later recurs is new. Each CSV contains the UTC receipt time, elapsed live time, live sequence, and every TelemetryParameterCatalog field. Millisecond timestamps and a process-local sequence keep filenames unique, and the UCSI log records each export success or failure.
<<<
RELATIONS:
- TYPE: Parent
  VALUE: RQ-UCSI-003
  ROLE: Refines

[DESIGN_ITEM]
UID: SDS-UCSI-004
TITLE: HVPS service commands
STATEMENT: >>>
The HVPS view presents command, setpoint, and feedback values together with HVPS interlock indicators. The UCSI view model sends operator HVPS commands through the GCB command interface and the UCSI HVPS UART command interface; returned telemetry updates the displayed feedback and interlock state. The emission control uses the same command path to request emission enable and disable.
<<<
RELATIONS:
- TYPE: Parent
  VALUE: RQ-UCSI-004
  ROLE: Refines

[DESIGN_ITEM]
UID: SDS-UCSI-005
TITLE: Coil service commands
STATEMENT: >>>
The Coils view presents operator command values and telemetry feedback values for the X, Y, and focus coils. The UCSI view model sends coil commands through the GCB command interface; returned telemetry updates the displayed coil feedback.
<<<
RELATIONS:
- TYPE: Parent
  VALUE: RQ-UCSI-005
  ROLE: Refines

[DESIGN_ITEM]
UID: SDS-UCSI-006
TITLE: Control system configuration
STATEMENT: >>>
The System Config view presents current control system configuration values with editable input values. The UCSI view model requests current configuration values and sends operator updates through the UCSI HVPS UART command interface.
<<<
RELATIONS:
- TYPE: Parent
  VALUE: RQ-UCSI-006
  ROLE: Refines

[DESIGN_ITEM]
UID: SDS-UCSI-007
TITLE: Version information presentation
STATEMENT: >>>
The UCSI view model obtains the CNC software version from the application assembly and, after system telemetry becomes available, requests the GCB and HVPS firmware versions through the GCB command interface. The System Status view presents the version strings and displays ``Unknown`` when version information is unavailable.
<<<
RELATIONS:
- TYPE: Parent
  VALUE: RQ-UCSI-007
  ROLE: Refines

[DESIGN_ITEM]
UID: SDS-UCSI-008
TITLE: Host-specific fault clearing
STATEMENT: >>>
The standalone composition registers a UCSI host-command implementation that routes the operator's Clear Faults command to the GCB command interface. The hosted system-PC composition overrides that implementation with one that reports fault clearing as unavailable. The UCSI view model enables Clear Faults only during live, non-recording operation when the selected host implementation permits it.
<<<
RELATIONS:
- TYPE: Parent
  VALUE: RQ-UCSI-008
  ROLE: Refines

[DESIGN_ITEM]
UID: SDS-UCSI-009
TITLE: HVPS fault-status decoding
STATEMENT: >>>
``HvpsTelemetryStatus`` decodes ``RawStatusFlags`` bits 10 through 19,
respectively, as Filament Clock Fault, Cathode Arc, Fan Fault, 24V Overcurrent
Fault, Master Fault, HV Overcurrent Fault, Temperature 1 Fault, Cathode
Overcurrent Fault, Temperature 3 Fault, and Temperature 2 Fault. These ten
faults are not decoded from ``RawIoFlags``.

The UCSI view model maps the decoded properties to the correspondingly named
HVPS-state indicators. A set bit produces an active indicator with value
``On``; a clear bit produces an inactive indicator with value ``Off``.
<<<
RELATIONS:
- TYPE: Parent
  VALUE: RQ-UCSI-009
  ROLE: Refines

[DESIGN_ITEM]
UID: SDS-UCSI-010
TITLE: Live-telemetry gate and one-point emission sequence
STATEMENT: >>>
``UcsiKeepaliveService`` is a singleton started by the UCSI view model. Its
single idempotent periodic loop sends a GCB version-information request every
second with a 500 ms timeout and
stops with the application cancellation token. It logs only the first warning
in a consecutive run of failures and permits a later failure to be logged after
a successful request.

The UCSI view model treats telemetry as current only in live mode when the
latest sample was received no more than 1500 ms earlier. The direct HVPS,
emission-directive, coil, and setpoint-refresh command paths
apply this freshness check and the command-specific control-state check before
calling a command interface. Replay, a missing or stale sample, or a
non-permitted state leaves the applicable controls unavailable and records the
reason without transmitting the operator-issued command.

The one-point Emission view validates acceleration potential, power, derived emission
current, filament current, duration, and coil currents against the configured service
limits. From ``Cold``, ``Primed``, or ``Staged``,
``RunEmissionSequenceAsync`` builds one operational point and drives the normal
command workflow. It returns a staged plan to ``Cold`` when necessary; from
``Cold`` it resets timers, clears a stale plan, performs warmup, and waits for
``Primed``. It then creates a session, waits for ``Staging``, loads and stages
the point, waits for ``Staged``, confirms the point, releases the plan, waits
for ``Ready``, releases the point, and waits for ``Emission``.

``WaitForControlStateAsync`` repeatedly checks fresh live telemetry and
advances only on the expected state; stale telemetry, a fault state, or another
terminal state fails the sequence. The Run/Stop command cancels an in-progress
sequence or sends ``Stop`` during a normal active state, and status text and the
UCSI log report each command and confirmed transition.
<<<
RELATIONS:
- TYPE: Parent
  VALUE: RQ-UCSI-010
  ROLE: Refines

[[/SECTION]]

[DOCUMENT]
TITLE: GBSK External GUI SW Verification Test Protocol
UID: DHF-GBSK-0047-TP
METADATA:
  COMPONENT: heracles-external-gui

[GRAMMAR]
IMPORT_FROM_FILE: @grammar

[[SECTION]]
TITLE: Purpose

[TEXT]
STATEMENT: >>>
This document provides the verification test protocol and execution results of the External GUI SW for the GBSK system. It defines the test cases that are used to verify the compliance of the software with the GBSK External GUI SW Verification Plan and Software Requirements Specification.
<<<

[[/SECTION]]

[[SECTION]]
TITLE: Scope

[TEXT]
STATEMENT: >>>
This document details all regression test cases for the Verification testing activities of GBSK External GUI Software. Each test case is designed to verify specific functional, interface, and usability requirements of the system, including treatment control, quality assurance, and operational workflows.
<<<

[[/SECTION]]

[[SECTION]]
TITLE: Abbreviations and Definitions

[TEXT]
STATEMENT: >>>
FW
Firmware

SDP
Software Development Plan

SVP
Software Verification Plan

SW
Software

GUI
Graphical User Interface

QA
Quality Assurance

DB
Database

GCB
Grid Control Board

HVPS
High Voltage Power Supply

MCU
Microcontroller Unit

LED
Light Emitting Diode

PID
Proportional Integral Derivative
<<<

[[/SECTION]]

[[SECTION]]
TITLE: References

[TEXT]
STATEMENT: >>>
GBSK SDP - DHF-GBSK-0001 Rev. 1

GBSK SVP - DHF-GBSK-0003 Rev. 1

GBSK External GUI SRS - DHF-GBSK-0007 Rev. 3

GBSK Software Architecture Description - DHF-GBSK-0004 Rev. 1

GBSK External GUI Verification Protocol - DHF-GBSK-0047 Rev. 1

GBSK External GUI Verification Execution Report - DHF-GBSK-0048 Rev. 1
<<<

[[/SECTION]]

[[SECTION]]
PREFIX: TC-H10TG-
TITLE: Test Cases

[TEST_CASE]
UID: TC-H10TG-58
TITLE: Treatment Console - Radiation Emission Control - Prepare process - Test Case
STATEMENT: >>>
Verify the user interface layout of the application accurately reflects the system's status and button labels during the treatment preparation process.
<<<
PREREQUISITES: >>>
Load a plan for treatment in the GBSK Internal unit.
<<<
STEPS: >>>
1. Log in to the External application. 

2. Navigate to the treatment view. 

3. Press the Prepare button to prepare the treatment.
<<<
EXPECTED_BEHAVIOR: >>>
1 - The interface should display the following states: 

System status: COLD 

Button Label: Prepare 

3 - The interface should display the following states: 

System status: WARMUP 

Button's label: Warming up ( with progress bar) 

then System status: HVSetup ( On Loading) 

Upon completion of the preparation process: 

System status: READY
<<<
RELATIONS:
- TYPE: Parent
  VALUE: RQ-H10TG-43
  ROLE: Verifies

[TEST_CASE]
UID: TC-H10TG-121
TITLE: Quality Assurance - Daily Warmup
STATEMENT: >>>
Verify the daily fast-warmup and conditioning controls use the deployed targets and report
a safety rejection without recording a completed procedure.
<<<
PREREQUISITES: >>>
1. The system is operational and can be returned to COLD state
2. Heater-current command telemetry and warmup history are available for observation
<<<
STEPS: >>>
1. Log in to the External application and navigate to Startup Cycle in Quality Assurance
2. In COLD state, engage either e-stop and attempt fast warmup
3. Release both e-stops, start fast warmup, and observe the commanded heater-current target
   and warmup history when the procedure completes
4. Return to COLD, start conditioning, and observe the commanded target and warmup history
   when the procedure completes
<<<
EXPECTED_BEHAVIOR: >>>
1. The rejected fast-warmup attempt displays an error that the current state is not
   permitted and directs the operator to verify both e-stops; no completed record is added
2. With both e-stops released, fast warmup commands its configured target and completion
   adds a record to warmup history.
3. Conditioning commands its configured target and completion adds a record to warmup history.
<<<
RELATIONS:
- TYPE: Parent
  VALUE: RQ-H10TG-1
  ROLE: Verifies
- TYPE: Parent
  VALUE: RQ-H10TG-29
  ROLE: Verifies
- TYPE: Parent
  VALUE: RQ-H10TG-30
  ROLE: Verifies

[TEST_CASE]
UID: TC-H10TG-62
TITLE: Radiation Emission Control - Emission Error Indicator - Test Case
STATEMENT: >>>
This test case aims to verify the application displays a visible indicator for an emission error in the system.
<<<
PREREQUISITES: >>>
1)Load a plan for treatment in the GBSK Internal unit.
<<<
STEPS: >>>
1. Log in to the External application. 

2. Navigate to the treatment view. 

3. Press the Prepare button to prepare the treatment. 

4. Press the Beam-On button to trigger emission delivery 

5. 

.Introduce a deliberate error in the firmware (e.g., trigger an e-stop interlock) .
<<<
EXPECTED_BEHAVIOR: >>>
A visible indicator is displayed to indicate a system error.
<<<
RELATIONS:
- TYPE: Parent
  VALUE: RQ-H10TG-5
  ROLE: Verifies

[TEST_CASE]
UID: TC-H10TG-98
TITLE: Treatment View - Patient Details - Test Case
STATEMENT: >>>
This test case aims to verify that the treatment console displays details about the treated patient and its treated site. The patient details shall include the following: • Patient's full name • MRN • Patient DOB • Field Name • Dose to be delivered • Applicator Size • Field/Shield Size • Devices • Setup Notes ( Simulation notes)
<<<
PREREQUISITES: >>>
Load a plan for treatment from the internal unit.
<<<
STEPS: >>>
1.Launch GBSK External 

2.Click the Treatment tab
<<<
EXPECTED_BEHAVIOR: >>>
The treatment console shall display details about the treated patient and its treated site. 

The patient details shall includes all required data
<<<
RELATIONS:
- TYPE: Parent
  VALUE: RQ-H10TG-85
  ROLE: Verifies

[TEST_CASE]
UID: TC-H10TG-101
TITLE: Treatment View - Telemetry - No communication to GCB indication - (UI) Test Case
STATEMENT: >>>
This test case aims to verify that the telemetry controls provide a clear indication when there is no communication with the GCB.
<<<
PREREQUISITES: >>>
Load a plan for treatment in GBSK Internal unit 

This test case requires the capability to generate a communication error with the GCB
<<<
STEPS: >>>
1.Launch GBSK External 

2.Click the Treatment tab 

3.Generate a deliberate communication error with the GCB
<<<
EXPECTED_BEHAVIOR: >>>
The telemetry controls shall provide a clear indication that there is no communication with the GCB. 

The System Status shall show - NO-COMM 

Timers, Energy, and Current shall show - ~0 ( around 0)
<<<
RELATIONS:
- TYPE: Parent
  VALUE: RQ-H10TG-82
  ROLE: Verifies

[TEST_CASE]
UID: TC-H10TG-114
TITLE: Quality Assurance - Daily Warmup - Error Indicator
STATEMENT: >>>
This test case verifies the handling of errors and faults in the system. It ensures appropriate responses to error conditions.
<<<
STEPS: >>>
1. Log in to the External application. 

2. Navigate to the Startup Cycle tab in the Quality Assurance view. 

3. Press Warmup. 

4. 

Simulate error ( i.e. activate interlock)
<<<
EXPECTED_BEHAVIOR: >>>
4 - Error indicator should be displayed on the view, and the user can click on it and see the error.
<<<
RELATIONS:
- TYPE: Parent
  VALUE: RQ-H10TG-1
  ROLE: Verifies
- TYPE: Parent
  VALUE: RQ-H10TG-53
  ROLE: Verifies

[TEST_CASE]
UID: TC-H10TG-295
TITLE: Resume Uncompleted Treatment Alert
STATEMENT: >>>
This test case verifies that the application alerts the operator if the loaded plan was not completely delivered and enables the operator to choose to deliver the remaining plan.
<<<
PREREQUISITES: >>>
Load a plan for treatment in the GBSK Internal unit.
<<<
STEPS: >>>
1. Log in to the External application. 

2. Navigate to the treatment view. 

3. Press the Prepare button to prepare the treatment. 

4. Press the Beam-On button to trigger emission delivery. 

5. Press the stop button 

6. Unload the plan 

7. Log in to the Internal application. 

8. Navigate to the treatment view. 

9. Load the plan into the external application. 

10. Go to the External application. 

11. Press the Prepare button to prepare the treatment.
<<<
EXPECTED_BEHAVIOR: >>>
5 - The emission process should be stopped, and the status should become primed. 

6 - The plan should be unloaded and removed from the UI. 

11 - An alert message should be displayed informing the user that the treatment was not delivered completely and it will resume the 
emission for the remaining time.
<<<
RELATIONS:
- TYPE: Parent
  VALUE: RQ-H10TG-161
  ROLE: Verifies
- TYPE: Parent
  VALUE: RQ-H10TG-160
  ROLE: Verifies

[TEST_CASE]
UID: TC-H10TG-131
TITLE: Treatment View - Alert for uncompleted Daily Safety checks - 2
STATEMENT: >>>
This test case verifies that appropriate alerts are displayed to the user when system conditions warrant notification. It validates the alert presentation and timing.
<<<
STEPS: >>>
1. log in to the External application. 

2. Navigate to the Safety Checks tab in the Quality Assurance view. 

3. Check all toggles ( toggle to green option) except for the door interlock and Save Quality checks. 

4. Navigate back to the treatment view. 

5. Press the Prepare button.
<<<
EXPECTED_BEHAVIOR: >>>
5 - An alert message pops up, advising the user that the treatment is not enabled if the daily safety checks are not completed.
<<<
RELATIONS:
- TYPE: Parent
  VALUE: RQ-H10TG-97
  ROLE: Verifies

[TEST_CASE]
UID: TC-H10TG-152
TITLE: Treatment View - Load a Treatment Plan
STATEMENT: >>>
This test case verifies the loading of treatment plans into the system. It validates that all plan parameters are correctly loaded and displayed.
<<<
STEPS: >>>
1. Log in to the External application. 

2. Navigate to the treatment view. 

3. Validate the plan parameters against the plan in the internal application. 

4. Press Prepre 

5. Press Beam-on
<<<
EXPECTED_BEHAVIOR: >>>
4 - Verify that energy in the telemetry panel is ramping up to the energy of the plan. 

5 - Verify that when emission is completed, the timer has reached the plan’s duration
<<<
RELATIONS:
- TYPE: Parent
  VALUE: RQ-H10TG-35
  ROLE: Verifies

[TEST_CASE]
UID: TC-H10TG-285
TITLE: Quality Assurance - Audit users' actions
STATEMENT: >>>
This test case verifies that system actions are properly logged and audited. It validates that the audit trail accurately records user actions and data modifications.
<<<
STEPS: >>>
1. Log in to the External application.

2. Navigate to the Beam QA Checks tab in the Quality Assurance view.

3. Select Energy 50/70/100 in the Energy drop-down.

4. Select exactly one emission in the Target list.

5. Press Prepare.

6. Press Beam On to start QC.
<<<
EXPECTED_BEHAVIOR: >>>
6 - The QualityCheck action triggered by the user is logged for the selected emission.
<<<
RELATIONS:
- TYPE: Parent
  VALUE: RQ-H10TG-1
  ROLE: Verifies
- TYPE: Parent
  VALUE: RQ-H10TG-89
  ROLE: Verifies
- TYPE: Parent
  VALUE: RQ-H10TG-280
  ROLE: Verifies
- TYPE: Parent
  VALUE: RQ-H10TG-66
  ROLE: Verifies
- TYPE: Parent
  VALUE: RQ-H10TG-53
  ROLE: Verifies

[TEST_CASE]
UID: TC-H10TG-116
TITLE: Treatment View - Database Communication Error
STATEMENT: >>>
This test case verifies proper error handling and reporting. It validates that appropriate error messages are displayed and logged when system errors occur.
<<<
PREREQUISITES: >>>
The database connection is available at test start and can be interrupted safely.
<<<
STEPS: >>>
1. Log in to the External application. 

2. Navigate to the treatment view. 

3. Press the Prepare button to prepare the treatment. 

4. Press the Beam-On button to trigger emission delivery. 

5. Interrupt the application's database connection during the emission.

6. Go to Log view.
<<<
EXPECTED_BEHAVIOR: >>>
6 - The application shall notify the operator that database communication was lost,
and the same communication error shall be displayed in the log list.
<<<
RELATIONS:
- TYPE: Parent
  VALUE: RQ-H10TG-288
  ROLE: Verifies

[TEST_CASE]
UID: TC-H10TG-80
TITLE: Warm-Up - Log Performed Warm Up - Test Case
STATEMENT: >>>
This test case verifies the system warmup and initialization process. It validates that the system is properly prepared for operation and all parameters are initialized.
<<<
STEPS: >>>
1. Launch GBSK SW External. (The external unit should be located outside the treatment room). 

2. Click the Prepare button. 

3. Click the Reset button 

4. Click the QC tab 

5. Click the Daily Warm-Up tab 

1. Go to Log tab
<<<
EXPECTED_BEHAVIOR: >>>
1. There shall be a log of all (Full and Fast) warm-ups performed during the system's lifetime. 

Test being executed 

TC-H10TG-80-#14 

Warm-Up - Log Performed 
Warm Up - Test Case 

13.
<<<
RELATIONS:
- TYPE: Parent
  VALUE: RQ-H10TG-57
  ROLE: Verifies

[TEST_CASE]
UID: TC-H10TG-65
TITLE: Treatment Console - Telemetry - (System status) - Test Case
STATEMENT: >>>
This test case verifies system status and monitoring capabilities. It validates that system state information is accurately displayed and updated.
<<<
STEPS: >>>
1. Log in to the External application. 

2. Navigate to the treatment view. 

3. Press the Prepare button to prepare the treatment. 

4. Press the Beam-On button to trigger emission delivery.
<<<
EXPECTED_BEHAVIOR: >>>
1 - The interface should display the following states: 

System status: COLD 

3 - The interface should display the following steps: 

System status: WARMUP 

then System status: HVSetup ( On Loading) 

Upon completion of the preparation process: 

System status: READY 

4 - The interface should display the following steps: 

System status: Emission 

Upon completion of the process: 

System status: Primed
<<<
RELATIONS:
- TYPE: Parent
  VALUE: RQ-H10TG-2
  ROLE: Verifies
- TYPE: Parent
  VALUE: RQ-H10TG-13
  ROLE: Verifies

[TEST_CASE]
UID: TC-H10TG-104
TITLE: Treatment View - Operational Point Emission Progress indicators - (Layout) Test Case
STATEMENT: >>>
This test case verifies the layout and user interface components of the Treatment View. It validates that all UI elements are properly displayed and arranged according to specifications.
<<<
PREREQUISITES: >>>
Load a plan for treatment in the GBSK Internal unit.
<<<
STEPS: >>>
1. Log in to the External application. 

2. Navigate to the treatment view. 

3. Press the Prepare button to prepare the treatment. 

4. Press the Beam-On button to trigger emission delivery.
<<<
EXPECTED_BEHAVIOR: >>>
1. The button label should transition to "Launching", and subsequently to "Beaming on" with a progress bar.
<<<
RELATIONS:
- TYPE: Parent
  VALUE: RQ-H10TG-95
  ROLE: Verifies
- TYPE: Parent
  VALUE: RQ-H10TG-10
  ROLE: Verifies
- TYPE: Parent
  VALUE: RQ-H10TG-4
  ROLE: Verifies

[TEST_CASE]
UID: TC-H10TG-294
TITLE: Users Authorization
STATEMENT: >>>
This test case verifies user authorization and access control. It validates that users can only access features they have permission to use.
<<<
PREREQUISITES: >>>
An authenticated test account without physics quality-assurance permission is available.
<<<
STEPS: >>>
1. Log in to the External application with the test account.

2. Navigate to the Quality Assurance view. 

3. Observe existing tabs.
<<<
EXPECTED_BEHAVIOR: >>>
2 - The Physics tab should not be available.
<<<
RELATIONS:
- TYPE: Parent
  VALUE: RQ-H10TG-287
  ROLE: Verifies

[TEST_CASE]
UID: TC-H10TG-293
TITLE: Physics View - Emission Process
STATEMENT: >>>
This test case verifies radiation emission control and safety. It validates that emission parameters are correctly managed and safety limits are enforced.
<<<
STEPS: >>>
1. Log in to the External application. 

2. Navigate to the Physics tab in the Quality Assurance view. 

3. Select the connected applicator size from the Applicator Size dropdown menu. 

4. Select the Energy level of the connected collimator. 

5. Enter duration of 10 sec. 

6. Press the Prepare button. 

7. Press Beam On button
<<<
EXPECTED_BEHAVIOR: >>>
6 - The interface should display the following states: 

System status: WARMUP 

Button's label: Warming up ( with progress bar) 

then System status: HVSetup ( On Loading) 

Upon completion of the preparation process: 

System status: READY 

7 - The button label should transition to "Launching", and subsequently to "Beaming on" with a progress bar. 

System status at the top of the screen should be "Emission". 

Upon completion, a pop-up message should be displayed to confirm successful emission.
<<<
RELATIONS:
- TYPE: Parent
  VALUE: RQ-H10TG-9
  ROLE: Verifies
- TYPE: Parent
  VALUE: RQ-H10TG-13
  ROLE: Verifies
- TYPE: Parent
  VALUE: RQ-H10TG-280
  ROLE: Verifies
- TYPE: Parent
  VALUE: RQ-H10TG-43
  ROLE: Verifies

[TEST_CASE]
UID: TC-H10TG-292
TITLE: Users Authorization
STATEMENT: >>>
This test case verifies user authorization and access control. It validates that users can only access features they have permission to use.
<<<
PREREQUISITES: >>>
An authenticated test account without treatment permission is available.
<<<
STEPS: >>>
1. Log in to the External application with the test account.

2. Observe the left panel menu.
<<<
EXPECTED_BEHAVIOR: >>>
2 - The Treatment menu item should not be available.
<<<
RELATIONS:
- TYPE: Parent
  VALUE: RQ-H10TG-287
  ROLE: Verifies

[TEST_CASE]
UID: TC-H10TG-124
TITLE: Treatment View - Warmup Progress Monitoring
STATEMENT: >>>
This test case verifies the system warmup and initialization process. It validates that the system is properly prepared for operation and all parameters are initialized.
<<<
STEPS: >>>
1. Log in to the External application. 

2. Navigate to the treatment view. 

3. Press the Prepare button to prepare the treatment.
<<<
EXPECTED_BEHAVIOR: >>>
3 - Verify that the button shows the progress of the warmup process.
<<<
RELATIONS:
- TYPE: Parent
  VALUE: RQ-H10TG-12
  ROLE: Verifies

[TEST_CASE]
UID: TC-H10TG-46
TITLE: Treatment Console - Radiation Emission Control - Beam On process - Test Case
STATEMENT: >>>
This test case verifies the functionality and status transitions of the GBSK External GUI during a treatment plan execution. To ensure that the system responds correctly to user interactions.
<<<
PREREQUISITES: >>>
Load a plan for treatment in the GBSK Internal unit.
<<<
STEPS: >>>
1. Log in to the External application. 

2. Navigate to the treatment view. 

3. Press the Prepare button to prepare the treatment. 

4. Press the Beam-On button to trigger emission delivery.
<<<
EXPECTED_BEHAVIOR: >>>
4 - The button label should transition to "Launching", and subsequently to "Beaming on" with a progress bar. 

System status at the top of the screen should be "Emission". 

Upon completion, a pop-up message should be displayed to confirm successful delivery. 

Upon approving the pop-up, the system status should change to "Termination" and the Energy level should go down to 0. 

6 - The button label should revert to "Beam On", and the system status should update to "Primed".
<<<
RELATIONS:
- TYPE: Parent
  VALUE: RQ-H10TG-9
  ROLE: Verifies

[TEST_CASE]
UID: TC-H10TG-136
TITLE: Quality Assurance - QC Measurement Acquisition and Diagnostics
STATEMENT: >>>
Verify that the QC path acquires detector measurements through main control, records the returned intensities, exposes detector diagnostic telemetry, and reports connection or acquisition failures.
<<<
PREREQUISITES: >>>
1. Run the External application with the GCB, main-control board, head, and QC detector connected.
2. Provide an approved QC detector signal source with distinguishable channel values and the ability to control detector connectivity.
3. Connect a UCSI diagnostic client that can subscribe to and record system telemetry.
<<<
STEPS: >>>
1. Log in to the External application and start recording system telemetry with the UCSI diagnostic client.

2. In the diagnostic client, observe both QC instantaneous readings, both QC accumulations, and
   both ADC connection states.

3. Navigate to the Beam QA Checks tab in the Quality Assurance view.

4. Select Energy 50/70/100 in the Energy drop-down and select exactly one emission in the Target list.

5. Press Prepare.

6. Press Beam On and observe the QC command trace until the selected emission completes.

7. Toggle to report view and compare the acquired channel 0 and channel 1 accumulation values.

8. Stop the diagnostic recording and inspect the recorded QC readings, accumulations, and ADC
connection states.

9. Disconnect the QC detector, select one emission again, and press Prepare.

10. Reconnect the detector, prepare the emission, arrange for QC start rejection and then for a
pending stop response beyond two seconds, and press Beam On for each case.
<<<
EXPECTED_BEHAVIOR: >>>
1 - UCSI records live QC diagnostic telemetry from the connected system.

2 - Both channel readings and accumulations are identified in counts, and both ADC connection
states reflect the connected detector hardware.

5 - Prepare succeeds only after the detector responds to the QC-board connection check through
main control.

6 - The trace sends ``[Start, 0]`` before Beam On and receives Armed before radiation is requested.
After the emission, ``[Stop, 0]`` responses are polled within one shared two-second deadline until
Complete. The five unsigned response words are channel 0 sum, channel 1 sum, channel 0 count,
channel 1 count, and numeric session status.

7 - The report contains exactly the selected Target for the selected Applicator and Energy level,
with exactly two measured accumulation rows and no rows for unselected Targets.

8 - UCSI records both live accumulation fields in schema version 2; replaying a version 1 recording
represents the absent accumulation fields as null rather than rejecting the file.

9 - Prepare returns the application to StandBy and displays a preparation error; no emission can
start while the detector is unavailable.

10 - Start rejection prevents Beam On and triggers one best-effort Stop. A stop deadline expiry
stops emission, displays an acquisition error, and creates no QC result.
<<<
RELATIONS:
- TYPE: Parent
  VALUE: RQ-H10TG-93
  ROLE: Verifies
- TYPE: Parent
  VALUE: RQ-H10TG-66
  ROLE: Verifies
- TYPE: Parent
  VALUE: RQ-H10TG-91
  ROLE: Verifies
- TYPE: Parent
  VALUE: RQ-H10TG-280
  ROLE: Verifies

[TEST_CASE]
UID: TC-H10TG-142
TITLE: Treatment View - Treatment Plan Execution Condition - 2
STATEMENT: >>>
This test case verifies treatment plan execution and delivery. It validates that treatments are properly executed according to plan specifications.
<<<
STEPS: >>>
1. Log in to the External application. 

2. Navigate to the treatment view. 

3. Observe the Prepare and Beam-On accessibility.
<<<
EXPECTED_BEHAVIOR: >>>
3 - The Prepare and Beam-On button should be disabled, and the operator can not activate emission
<<<
RELATIONS:
- TYPE: Parent
  VALUE: RQ-H10TG-36
  ROLE: Verifies

[TEST_CASE]
UID: TC-H10TG-149
TITLE: Treatment View - Treatment Plan Confirmation
STATEMENT: >>>
This test verifies that one valid treatment field produces one scalar firmware session.
<<<
STEPS: >>>
Automated test:

1. Run the treatment-plan field-rule and single-emission main-board contract tests.
<<<
EXPECTED_BEHAVIOR: >>>
1. Verify missing, null, and additional treatment fields are rejected before a firmware command is sent.
2. Verify one valid treatment field sends one new-session request with no payload.
3. Verify one load and one confirmation carry one scalar emission without point metadata.
<<<
RELATIONS:
- TYPE: Parent
  VALUE: RQ-H10TG-9
  ROLE: Verifies
- TYPE: Parent
  VALUE: RQ-H10TG-31
  ROLE: Verifies
- TYPE: Parent
  VALUE: RQ-H10TG-32
  ROLE: Verifies
- TYPE: Parent
  VALUE: RQ-H10TG-34
  ROLE: Verifies
- TYPE: Parent
  VALUE: RQ-H10TG-35
  ROLE: Verifies

[TEST_CASE]
UID: TC-H10TG-78
TITLE: Enable window switching after emission delivery - (unlock layout) Test Case
STATEMENT: >>>
Verify that the layout unlocks when the emission is completed, allowing navigation to other tabs.
<<<
PREREQUISITES: >>>
Load a plan for treatment in the GBSK Internal unit.
<<<
STEPS: >>>
1. Log in to the External application. 

2. Navigate to the treatment view. 

3. Press the Prepare button to prepare the treatment. 

4. Press the Beam-On button to trigger emission delivery. 

5. Click the Log tab 

6. Upon completion of the emission, approve the confirmation pop-up. 

7. Click the Log tab
<<<
EXPECTED_BEHAVIOR: >>>
1. The user should be able to navigate to Log view. 

2. The layout should be unlocked so the user can navigate to all views.
<<<
RELATIONS:
- TYPE: Parent
  VALUE: RQ-H10TG-52
  ROLE: Verifies

[TEST_CASE]
UID: TC-H10TG-112
TITLE: Treatment View - Reset Timers and Unload Plan after Treatment is Completed
STATEMENT: >>>
This test case verifies the loading of treatment plans into the system. It validates that all plan parameters are correctly loaded and displayed.
<<<
STEPS: >>>
1. Log in to the External application. 

2. Navigate to the treatment view. 

3. Press the Prepare button to prepare the treatment. 

4. Press the Beam-On button to trigger emission delivery. 

5. Wait until the plan is delivered and the pop-up appears. 

6. Press ok button
<<<
EXPECTED_BEHAVIOR: >>>
5. A pop message should be displayed informing the user that the emission is finished and by pressing the OK button, the timers will be 
reset and the plan will unload. 

6. The timers in the telemetry block will show 0, and the plan will disappear from the view.
<<<
RELATIONS:
- TYPE: Parent
  VALUE: RQ-H10TG-105
  ROLE: Verifies

[TEST_CASE]
UID: TC-H10TG-118
TITLE: Treatment View - Emission audible indicator
STATEMENT: >>>
This test case verifies radiation emission control and safety. It validates that emission parameters are correctly managed and safety limits are enforced.
<<<
STEPS: >>>
1. Log in to the External application. 

2. Navigate to the treatment view. 

3. Press the Prepare button to prepare the treatment. 

4. Press the Beam-On button to trigger emission delivery.
<<<
EXPECTED_BEHAVIOR: >>>
4 - There should be a plus of half a second on/off audible sound.
<<<
RELATIONS:
- TYPE: Parent
  VALUE: RQ-H10TG-87
  ROLE: Verifies

[TEST_CASE]
UID: TC-H10TG-100
TITLE: Quality Assurance - Quality Checks Reports - (UI) Test Case
STATEMENT: >>>
This test case is designed to verify that the application provide the operator with an interface displaying the history of quality test results.
<<<
PREREQUISITES: >>>
Conduct quality checks within the system prior to conducting this test
<<<
STEPS: >>>
Test Steps: 

1.Launch GBSK External 

2.Click the Quality Assurance tab 

3.Inside the Quality Assurance tab, click the Quality Checks tab
<<<
EXPECTED_BEHAVIOR: >>>
The interface shall display the history of quality test results. 

The results will include the current and intensity for each requested QA emission.

The operator will be able to filter the results by the collimator type, energy level, and the date the test was performed.
<<<
RELATIONS:
- TYPE: Parent
  VALUE: RQ-H10TG-93
  ROLE: Verifies

[TEST_CASE]
UID: TC-H10TG-102
TITLE: Quality Assurance - Daily Warmup - Inspect Errors - Test Case
STATEMENT: >>>
This test case aims to verify that the user can view errors that occurred during daily warmup.
<<<
PREREQUISITES: >>>
Intentionally create errors ( e.g., interlocks) during Daily Warmup
<<<
STEPS: >>>
1.Launch GBSK External 

2.Click the Quality Assurance tab 

3.Inside the Quality Assurance tab, click the Daily Warmup tab 

4.Click the error indicator
<<<
EXPECTED_BEHAVIOR: >>>

4.The user shall be able to view the errors that occurred .
<<<
RELATIONS:
- TYPE: Parent
  VALUE: RQ-H10TG-1
  ROLE: Verifies
- TYPE: Parent
  VALUE: RQ-H10TG-53
  ROLE: Verifies

[TEST_CASE]
UID: TC-H10TG-144
TITLE: Treatment View - Treatment Plan Execution Condition - 4
STATEMENT: >>>
This test case verifies treatment plan execution and delivery. It validates that treatments are properly executed according to plan specifications.
<<<
STEPS: >>>
1. log in to the External application. 

2. Navigate to the treatment view. 

3. Activate E-Stop interlock
<<<
EXPECTED_BEHAVIOR: >>>
3- The Prepare and Beam-On button should be disabled, and the operator can not activate emission
<<<
RELATIONS:
- TYPE: Parent
  VALUE: RQ-H10TG-36
  ROLE: Verifies

[TEST_CASE]
UID: TC-H10TG-70
TITLE: Treatment Console - Restrict window switching after Prepare - Test Case
STATEMENT: >>>
Verify that the user is unable to switch to other views after pressing the “Prepare” button. The treatment tab should remain locked.
<<<
PREREQUISITES: >>>
Load a plan for treatment in the GBSK Internal unit.
<<<
STEPS: >>>
1. Log in to the External application. 

2. Navigate to the treatment view. 

3. Press the Prepare button to prepare the treatment. 

4. Click the Log tab
<<<
EXPECTED_BEHAVIOR: >>>
1. The user should be able to navigate to the Log view.
<<<
RELATIONS:
- TYPE: Parent
  VALUE: RQ-H10TG-49
  ROLE: Verifies
- TYPE: Parent
  VALUE: RQ-H10TG-52
  ROLE: Verifies

[TEST_CASE]
UID: TC-H10TG-148
TITLE: Treatment View - Confirmation of Treatment Plan
STATEMENT: >>>
This test verifies that scalar parameters are confirmed only after staging succeeds.
<<<
STEPS: >>>
Automated test:

1. Run the single-emission main-board contract tests.
<<<
EXPECTED_BEHAVIOR: >>>
1. Verify confirmation is sent in Staged for the same scalar emission that was loaded.
<<<
RELATIONS:
- TYPE: Parent
  VALUE: RQ-H10TG-35
  ROLE: Verifies
- TYPE: Parent
  VALUE: RQ-H10TG-34
  ROLE: Verifies

[TEST_CASE]
UID: TC-H10TG-81
TITLE: Treatment Console - Radiation Emission Control - Resume Beam On process after error is cleared - Test Case
STATEMENT: >>>
Verify that Resume reconfirms and releases the same scalar emission and remaining time
after an error is cleared.
<<<
PREREQUISITES: >>>
1)Create treatment field with duration of 12 Seconds and Load a plan for treatment in the GBSK Internal unit . 

2) The ability to intentionally create an error in the system.
<<<
STEPS: >>>
1. Log in to the External application. 

2. Navigate to the treatment view. 

3. Press the Prepare button to prepare the treatment. 

4. Press the Beam-On button to trigger emission delivery. 

5. After 8 seconds (check elapsed time), create an intended error in the system (e.g., activate the e-stop) 

6. Observe the error 

7. Click the Clear Error button 

8. Click the Resume button.
<<<
EXPECTED_BEHAVIOR: >>>
When the resume process is triggered, the emission should resume for the remaining duration (4 Seconds).
<<<
RELATIONS:
- TYPE: Parent
  VALUE: RQ-H10TG-73
  ROLE: Verifies

[TEST_CASE]
UID: TC-H10TG-132
TITLE: Treatment View - Alert for uncompleted Daily Safety checks - 3
STATEMENT: >>>
This test case verifies that appropriate alerts are displayed to the user when system conditions warrant notification. It validates the alert presentation and timing.
<<<
STEPS: >>>
1. Log in to the External application. 

2. Navigate to the Safety Checks tab in the Quality Assurance view. 

3. Check all toggles ( toggle to green option) except for the normal stop and Save Quality checks. 

4. Navigate back to the treatment view. 

5. Press the Prepare button.
<<<
EXPECTED_BEHAVIOR: >>>
5 - An alert message pops up, advising the user that the treatment is not enabled if the daily safety checks are not completed.
<<<
RELATIONS:
- TYPE: Parent
  VALUE: RQ-H10TG-97
  ROLE: Verifies

[TEST_CASE]
UID: TC-H10TG-60
TITLE: Radiation Emission Control - Record partial treatment - Test Case
STATEMENT: >>>
This test case verifies radiation emission control and safety. It validates that emission parameters are correctly managed and safety limits are enforced.
<<<
STEPS: >>>
1. Log in to the External application. 

2. Navigate to the treatment view. 

3. Press the Prepare button to prepare the treatment. 

4. Press the Beam-On button to trigger emission delivery. 

5. 

Click the Stop button (during the beaming process) 

6. Click to approve the pop-up message indicating that the beaming has stopped 

7. Open the Internal application. 

8. Open the Treatment tab of the treated patient and locate the recorded treatment.
<<<
EXPECTED_BEHAVIOR: >>>
A partial treatment record should appear in the treatment table.
<<<
RELATIONS:
- TYPE: Parent
  VALUE: RQ-H10TG-22
  ROLE: Verifies

[TEST_CASE]
UID: TC-H10TG-130
TITLE: Treatment View - Alert for uncompleted Daily Safety checks - 1
STATEMENT: >>>
This test case verifies that appropriate alerts are displayed to the user when system conditions warrant notification. It validates the alert presentation and timing.
<<<
STEPS: >>>
1. log in to the External application. 

2. Navigate to the Safety Checks tab in the Quality Assurance view. 

3. Check ( toggle to green option) all toggles except e-Stop and Save Quality checks. 

5. Navigate back to the treatment view. 

6. Press the Prepare button.
<<<
EXPECTED_BEHAVIOR: >>>
6 - An alert message pops up, advising the user that the treatment is not enabled if the daily safety checks are not completed.
<<<
RELATIONS:
- TYPE: Parent
  VALUE: RQ-H10TG-97
  ROLE: Verifies

[TEST_CASE]
UID: TC-H10TG-141
TITLE: Treatment View - Treatment Plan Execution Condition - 1
STATEMENT: >>>
This test case verifies treatment plan execution and delivery. It validates that treatments are properly executed according to plan specifications.
<<<
STEPS: >>>
1. Log in to the External application. 

2. Navigate to the treatment view. 

3. Observe the Prepare and Beam-On accessibility.
<<<
EXPECTED_BEHAVIOR: >>>
3 - The Prepare and Beam-On button should be disabled, and the operator can not activate emission
<<<
RELATIONS:
- TYPE: Parent
  VALUE: RQ-H10TG-36
  ROLE: Verifies

[TEST_CASE]
UID: TC-H10TG-145
TITLE: Treatment View - Treatment Plan Staging - 1
STATEMENT: >>>
This test case verifies treatment plan operations and management. It ensures that treatment plans are properly created, modified, and applied.
<<<
STEPS: >>>
White box testing: 

1. Open xcc solution in an IDE ( Visual Studio or VSCode). 

2. Search where GcbStateNew.Primed is used.
<<<
EXPECTED_BEHAVIOR: >>>
2 - Verify that it is used as a condition for staging the treatment
<<<
RELATIONS:
- TYPE: Parent
  VALUE: RQ-H10TG-31
  ROLE: Verifies

[TEST_CASE]
UID: TC-H10TG-151
TITLE: Treatment View - Initialize the System
STATEMENT: >>>
This test case verifies the functionality and operation of Treatment View. It validates that the component behaves according to specifications and system requirements.
<<<
STEPS: >>>
1. Restart the machine (gcb) 

2. Observe the system status as it restarts.
<<<
EXPECTED_BEHAVIOR: >>>
2 - Verify that the status changed from Startup to Cold.
<<<
RELATIONS:
- TYPE: Parent
  VALUE: RQ-H10TG-26
  ROLE: Verifies

[TEST_CASE]
UID: TC-H10TG-44
TITLE: Treatment Console - Radiation Emission Control - Layout - Test Case
STATEMENT: >>>
This test case verifies the layout and user interface components of the Treatment Console. It validates that all UI elements are properly displayed and arranged according to specifications.
<<<
PREREQUISITES: >>>
Load a plan for treatment in the GBSK Internal unit. 

Verify the existence of an interface through which the user can initiate radiation delivery in accordance with a predefined treatment plan.
<<<
STEPS: >>>
1. Log in to the External application. 

2. Navigate to the treatment view.
<<<
EXPECTED_BEHAVIOR: >>>
2 - The layout of the main (treatment) view includes the following: 

A table listing the treatment fields of the plan. 

System telemetry view including: System status, Main timer (in seconds), Backup Timer 1 (in seconds), Backup Timer 2 (in seconds), 
Energy (in KV), Current (in mA). 

Action panel: 

• Prepare button 

• Beam on 

• Stop button 

Interlock icon 

System Signal icon 

Live Camera view to monitor the patient.
<<<
RELATIONS:
- TYPE: Parent
  VALUE: RQ-H10TG-13
  ROLE: Verifies

[TEST_CASE]
UID: TC-H10TG-289
TITLE: Keyboard Adjustable Position
STATEMENT: >>>
This test case verifies the functionality and operation of Keyboard Adjustable Position. It validates that the component behaves according to specifications and system requirements.
<<<
STEPS: >>>
1. Log in to the External application. 

2. Press the keyboard icon in the bottom-right corner. 

3. Adjust the position of the keyboard by pressing the arrows on the frame
<<<
EXPECTED_BEHAVIOR: >>>
The keyboard position should be changed according to the selected arrow.
<<<
RELATIONS:
- TYPE: Parent
  VALUE: RQ-H10TG-281
  ROLE: Verifies

[TEST_CASE]
UID: TC-H10TG-126
TITLE: Treatment View - Error Handling Received From Firmware
STATEMENT: >>>
This test case verifies proper error handling and reporting. It validates that appropriate error messages are displayed and logged when system errors occur.
<<<
STEPS: >>>
1. Log in to the External application. 

2. Navigate to the treatment view. 

3. Press the Prepare button to prepare the treatment. 

4. Activate some interlock ( e.g., E-stop) . 

5. Open Log viewer
<<<
EXPECTED_BEHAVIOR: >>>
5 - Verify that the error from FW is logged the system readiness status.
<<<
RELATIONS:
- TYPE: Parent
  VALUE: RQ-H10TG-283
  ROLE: Verifies
- TYPE: Parent
  VALUE: RQ-H10TG-285
  ROLE: Verifies

[TEST_CASE]
UID: TC-H10TG-69
TITLE: Treatment Console - Radiation Emission Control - Stopped Emission Info Pop Up - Test Case
STATEMENT: >>>
Verify that upon pressing the stop button, an informative pop-up message is displayed, indicating that the emission has been halted. Ensure the layout and UI elements function correctly.
<<<
PREREQUISITES: >>>
Load a plan for treatment in the GBSK Internal unit.
<<<
STEPS: >>>
1. Log in to the External application. 

2. Navigate to the treatment view. 

3. Press the Prepare button to prepare the treatment. 

4. Press the Beam-On button to trigger emission delivery. 

5. Wait until the system enters the Emission state.

6. Press the Stop button to stop the emission.
<<<
EXPECTED_BEHAVIOR: >>>
1. After the user presses the stop button, an information pop-up message shall indicate that the emission has been halted.
<<<
RELATIONS:
- TYPE: Parent
  VALUE: RQ-H10TG-3
  ROLE: Verifies

[TEST_CASE]
UID: TC-H10TG-133
TITLE: Treatment View - Alert for uncompleted Daily Safety checks - 4
STATEMENT: >>>
This test case verifies that appropriate alerts are displayed to the user when system conditions warrant notification. It validates the alert presentation and timing.
<<<
STEPS: >>>
1. log in to the External application. 

2. Navigate to the Safety Checks tab in the Quality Assurance view. 

3. Check all toggles ( toggle to green option) except for the X-ray light, X-ray sound, live video stream, and Save Quality checks. 

4. Navigate back to the treatment view. 

5. Press the Prepare button.
<<<
EXPECTED_BEHAVIOR: >>>
5 - The Prepare process starts.
<<<
RELATIONS:
- TYPE: Parent
  VALUE: RQ-H10TG-97
  ROLE: Verifies

[TEST_CASE]
UID: TC-H10TG-143
TITLE: Treatment View - Treatment Plan Execution Condition - 3
STATEMENT: >>>
This test case verifies treatment plan execution and delivery. It validates that treatments are properly executed according to plan specifications.
<<<
STEPS: >>>
1. Log in to the External application. 

2. Navigate to the treatment view. 

3. Activate Base Key interlock
<<<
EXPECTED_BEHAVIOR: >>>
3 - The Prepare and Beam-On button should be disabled, and the operator can not activate emission
<<<
RELATIONS:
- TYPE: Parent
  VALUE: RQ-H10TG-36
  ROLE: Verifies

[TEST_CASE]
UID: TC-H10TG-79
TITLE: Enable window switching after emission delivery - (unload a plan) - Test Case
STATEMENT: >>>
Verify that the layout unlocks correctly and that the Clear button unloads the Plan.
<<<
PREREQUISITES: >>>
Load a plan for treatment in the GBSK Internal unit.
<<<
STEPS: >>>
1.Launch GBSK SW External . (The external unit should be located outside the treatment room). 

2.Click the Prepare button. 

3.Click the Beam On button. 

4.Upon completion of the emission, Approve confirmation.
<<<
EXPECTED_BEHAVIOR: >>>
The plan should be unloaded and view should be cleared
<<<
RELATIONS:
- TYPE: Parent
  VALUE: RQ-H10TG-52
  ROLE: Verifies

[TEST_CASE]
UID: TC-H10TG-150
TITLE: Treatment View - Filament Conditioning
STATEMENT: >>>
This test case verifies the functionality and operation of Treatment View. It validates that the component behaves according to specifications and system requirements.
<<<
STEPS: >>>
White box testing: 

1. Open xcc solution in an IDE ( Visual Studio or VSCode). 

2. Search for the Conditioning function.
<<<
EXPECTED_BEHAVIOR: >>>
2 - verify that the application checks that the input Conditioning function is within the valid operational limits.
<<<
RELATIONS:
- TYPE: Parent
  VALUE: RQ-H10TG-29
  ROLE: Verifies

[TEST_CASE]
UID: TC-H10TG-59
TITLE: Treatment Console - Radiation Emission Control - Emission Progress indicators - Test Case
STATEMENT: >>>
This test case verifies radiation emission control and safety. It validates that emission parameters are correctly managed and safety limits are enforced.
<<<
STEPS: >>>
1. Log in to the External application. 

2. Navigate to the treatment view. 

3. Press the Prepare button to prepare the treatment. 

4. Press the Beam-On button to trigger emission delivery.
<<<
EXPECTED_BEHAVIOR: >>>
\*There shall be an X-ray exposure timer indicating the elapsed emission time. 

\*There shall be a visual indicator, a progress bar, representing the progress of radiation.
<<<
RELATIONS:
- TYPE: Parent
  VALUE: RQ-H10TG-95
  ROLE: Verifies
- TYPE: Parent
  VALUE: RQ-H10TG-10
  ROLE: Verifies
- TYPE: Parent
  VALUE: RQ-H10TG-4
  ROLE: Verifies

[TEST_CASE]
UID: TC-H10TG-111
TITLE: Quality Assurance - Perform System Safety Checks
STATEMENT: >>>
This test case verifies quality assurance checks and validations. It ensures that the system properly executes quality control procedures.
<<<
STEPS: >>>
1. log in to the External application. 

2. Navigate to the Quality Assurance view. 

3. Press the Prepare button to prepare the treatment. 

4. Press the Beam-On button to trigger emission delivery. 

5. Toggle the buttons ( combine success and fail ( red and green) 

1. Press the save button. 

2. 

Toggle to report
<<<
EXPECTED_BEHAVIOR: >>>
5 - The user can toggle the button to green ( success) or red ( failure) 

7 - Make sure the result is saved and displayed in the report.
<<<
RELATIONS:
- TYPE: Parent
  VALUE: RQ-H10TG-91
  ROLE: Verifies
- TYPE: Parent
  VALUE: RQ-H10TG-92
  ROLE: Verifies
- TYPE: Parent
  VALUE: RQ-H10TG-106
  ROLE: Verifies
- TYPE: Parent
  VALUE: RQ-H10TG-93
  ROLE: Verifies
- TYPE: Parent
  VALUE: RQ-H10TG-66
  ROLE: Verifies

[TEST_CASE]
UID: TC-H10TG-153
TITLE: Treatment View - Plan details view
STATEMENT: >>>
This test case verifies treatment plan operations and management. It ensures that treatment plans are properly created, modified, and applied.
<<<
STEPS: >>>
1. Log in to the External application. 

2. Navigate to the treatment view.
<<<
EXPECTED_BEHAVIOR: >>>
2- Validate that plan treatment against the plan loaded from the internal application. Validate all parameters for the treatment: 

• Energy level [kVp]. 

• Duration [sec]. 

• Current [mA]. 

• Actual is 0 

• Remaining equal to duration
<<<
RELATIONS:
- TYPE: Parent
  VALUE: RQ-H10TG-8
  ROLE: Verifies

[TEST_CASE]
UID: TC-H10TG-64
TITLE: Radiation Emission Control - Clear Fault Flags - Test case
STATEMENT: >>>
This test case verifies the handling of errors and faults in the system. It ensures appropriate responses to error conditions.
<<<
STEPS: >>>
1. Log in to the External application. 

2. Navigate to the treatment view. 

3. Press the Prepare button to prepare the treatment. 

4. Press the Beam-On button to trigger emission delivery 

5. 

.Introduce a deliberate error in the firmware (e.g., trigger an e-stop interlock) . 

6. Fix the error ( open the E-Stop button) 

7. Press Clear Error.
<<<
EXPECTED_BEHAVIOR: >>>
5 - When the device transitions to FAULT mode, an option (button) shall be available in the interface to clear fault flags. 

7 - After clearing the error and pressing the button, the fault condition is reset, and the error disappears.
<<<
RELATIONS:
- TYPE: Parent
  VALUE: RQ-H10TG-284
  ROLE: Verifies

[TEST_CASE]
UID: TC-H10TG-135
TITLE: Quality Assurance - Perform Quality Checks - Deviation
STATEMENT: >>>
This test case verifies QC deviation reporting and every QC acceptance decision used to gate
treatment preparation.
<<<
PREREQUISITES: >>>
1. Store two referenced QC samples for one collimator and energy configuration, with the newer
   reference containing known nonzero diode values and unused zero-valued channels.
2. Make the latest reference more than 24 hours old.
<<<
STEPS: >>>
1. Log in to GBSK External and open Beam QA Checks.
2. Select the same collimator, energy, and QA emission as the stored references.
3. Prepare and emit a current QC sample within 24 hours of the test.
4. Open the report view, select the configuration, inspect the reference and latest results,
   switch to Deviation, and independently calculate each displayed deviation.
5. Exercise samples just inside and just outside positive and negative 3 percent deviation.
6. Exercise matching zero values, a nonzero value against a zero reference, a missing QA
   emission, and a mismatched diode-value count.
7. Exercise a configuration with no samples, one whose latest sample is older than 24 hours,
   and a current unapproved sample with no reference.
8. Mark the current sample approved and repeat the acceptance evaluation without a reference.
9. Run the QC treatment acceptance service tests.
<<<
EXPECTED_BEHAVIOR: >>>
1. Reporting and acceptance use the newest reference and the newest current sample for the
   selected configuration.
2. Displayed deviations match the independent calculations.
3. A sample passes only when every available diode value has an absolute deviation of less
   than 3 percent; deviation outside the limit in either direction fails the sample.
4. Matching zero values have zero deviation. A nonzero value against a zero reference, missing
   or null data, or a mismatched QA-emission or diode-value shape fails acceptance.
5. No sample or a latest sample older than 24 hours returns ``Missing``; a current unapproved
   sample without a reference returns ``NoReference``.
6. A current sample with persisted approval returns ``Accepted`` without a reference.
7. The automated tests produce the same status for every boundary and data-shape case.
<<<
RELATIONS:
- TYPE: Parent
  VALUE: RQ-H10TG-93
  ROLE: Verifies
- TYPE: Parent
  VALUE: RQ-H10TG-66
  ROLE: Verifies
- TYPE: Parent
  VALUE: RQ-H10TG-94
  ROLE: Verifies
- TYPE: Parent
  VALUE: RQ-H10TG-91
  ROLE: Verifies
- TYPE: Parent
  VALUE: RQ-H10TG-280
  ROLE: Verifies
- TYPE: Parent
  VALUE: RQ-H10TG-282
  ROLE: Verifies

[TEST_CASE]
UID: TC-H10TG-113
TITLE: Treatment View - Plan details view
STATEMENT: >>>
This test case verifies treatment plan operations and management. It ensures that treatment plans are properly created, modified, and applied.
<<<
STEPS: >>>
1. Log in to the External application. 

2. Navigate to the treatment view.
<<<
EXPECTED_BEHAVIOR: >>>
2 - The application displays the following data in the plan detail: 

The Treatment Plan parameters: Energy level [kVp], Duration [sec], Current [mA], Actual duration [sec] 

Remaining duration [sec].
<<<
RELATIONS:
- TYPE: Parent
  VALUE: RQ-H10TG-8
  ROLE: Verifies

[TEST_CASE]
UID: TC-H10TG-77
TITLE: Treatment Console - Restrict window switching during active emission - Test Case
STATEMENT: >>>
Verify that the user can not navigate to any view during the emission process.
<<<
PREREQUISITES: >>>
Load a treatment plan in the GBSK Internal unit.
<<<
STEPS: >>>
1. Log in to the External application. 

2. Navigate to the treatment view. 

3. Press the Prepare button to prepare the treatment. 

4. Press the Beam-On button to trigger emission delivery. 

5. Click the Log tab
<<<
EXPECTED_BEHAVIOR: >>>
1. The user should be able to navigate to Log view.
<<<
RELATIONS:
- TYPE: Parent
  VALUE: RQ-H10TG-49
  ROLE: Verifies

[TEST_CASE]
UID: TC-H10TG-288
TITLE: QC Approval Authentication, Persistence, and Treatment Gate
STATEMENT: >>>
This test case verifies that failed QC results and an excessive magnetometer correction-value
delta block treatment, that QC approval requires authentication, and that rejected and
successful approval decisions persist correctly.
<<<
PREREQUISITES: >>>
1. Store a current failed QC result for the configuration required by a treatment plan.
2. Provision a user with a known username, password, and email address.
3. Store Front and Back Magnetometer Correction Matrix values whose delta exceeds the
   configured ``maxMagnetomerDiff`` for the treatment configuration.
<<<
STEPS: >>>
1. In GBSK External, load the treatment plan and press Prepare.
2. In GBSK Internal, open the Quality Assurance approval interface and attempt to approve
   the failed result with an unknown username and then with the known username and an incorrect
   password.
3. Restart GBSK Internal, reopen the QC result, and inspect its approval state.
4. Approve the same result using a case variant of the known username and its correct password.
5. Restart GBSK Internal, reopen the result, and inspect the stored approver.
6. Return to the treatment plan in GBSK External and press Prepare.
7. Run the SQLite QC approval persistence tests.
8. With the excessive magnetometer delta still stored, load the applicable treatment plan and
   press Prepare.
9. Reduce the stored delta to the configured limit or below, reload the plan, and press Prepare.
10. Using disposable accounts with persisted failed-login counts below 10 and at least 10, attempt QC approval with incorrect and correct passwords. Inspect both the approval state and failed-login counts after each attempt.
<<<
EXPECTED_BEHAVIOR: >>>
1. The unapproved failed result blocks Prepare and produces the QC failure indication.
2. Both invalid approval attempts are rejected as unauthenticated and leave the result
   unapproved after restart.
3. Valid credentials approve the selected result, and the user's email address remains stored
   as the approver after restart.
4. Username matching accepts the tested case variant; the password must match.
5. The current approved result is accepted and no longer blocks Prepare.
6. The automated tests confirm rejection without mutation, persisted approver identity for
   valid credentials, and a not-found response for a nonexistent sample after authentication.
7. The excessive magnetometer delta blocks Prepare and identifies the correction-value
   constraint.
8. At or below the configured limit, the magnetometer check no longer blocks Prepare.
9. The locked account cannot approve even with its correct password. Below the threshold, valid credentials can approve and invalid credentials cannot. Neither successful nor rejected approval changes failed-login attempts.
<<<
RELATIONS:
- TYPE: Parent
  VALUE: RQ-H10TG-282
  ROLE: Verifies
- TYPE: Parent
  VALUE: RQ-H10TG-247
  ROLE: Verifies

[TEST_CASE]
UID: TC-H10TG-103
TITLE: Quality Assurance - Daily Warmup - Clear Errors - (UI) Test Case
STATEMENT: >>>
This test case aims to verify that the application provides a control that allows the user to clear latched fault flags that occurred during the daily (Full) Warmup process.
<<<
PREREQUISITES: >>>
Intentionally create Daily Warmup errors in the system prior to conducting this test
<<<
STEPS: >>>
1.Launch GBSK External 

2.Click the Quality Assurance tab 

3.Inside the Quality Assurance tab, click the Daily Warmup tab 

4.Click the the Clear Error button
<<<
EXPECTED_BEHAVIOR: >>>
It should Clear latched fault flags that occurred during the daily (Full) Warmup process. 

This capability will allow the application to reset fault conditions after the fault is addressed or reviewed.
<<<
RELATIONS:
- TYPE: Parent
  VALUE: RQ-H10TG-1
  ROLE: Verifies
- TYPE: Parent
  VALUE: RQ-H10TG-53
  ROLE: Verifies

[TEST_CASE]
UID: TC-H10TG-296
TITLE: Resume Uncompleted Treatment
STATEMENT: >>>
This test case verifies that the application enables the operator to resume an uncompleted treatment.
<<<
PREREQUISITES: >>>
Load a plan for treatment in the GBSK Internal unit.
<<<
STEPS: >>>
1. Log in to the External application. 

2. Navigate to the treatment view. 

3. Press the Prepare button to prepare the treatment. 

4. Press the Beam-On button to trigger emission delivery. 

5. Press the stop button 

6. Unload the plan 

7. Log in to the Internal application. 

8. Navigate to the treatment view. 

9. Load the plan into the external application. 

10. Go to the External application. 

11. Press the Prepare button to prepare the treatment. 

12. Press Beam on.
<<<
EXPECTED_BEHAVIOR: >>>
The emission process should be stopped, and the status should become primed. 

6 - The plan should be unloaded and removed from the UI. 

11 - An alert message should be displayed informing the user that the treatment was not delivered completely and it will resume the 
emission for the remaining time. 

12 - The emission should run for the remining time.
<<<
RELATIONS:
- TYPE: Parent
  VALUE: RQ-H10TG-161
  ROLE: Verifies
- TYPE: Parent
  VALUE: RQ-H10TG-160
  ROLE: Verifies

[TEST_CASE]
UID: TC-H10TG-120
TITLE: Quality Assurance - Daily Warmup - Progress Monitoring
STATEMENT: >>>
This test case verifies quality assurance checks and validations. It ensures that the system properly executes quality control procedures.
<<<
STEPS: >>>
1. Log in to the External application. 

2. Navigate to the Startup Cycle tab in the Quality Assurance view. 

3. Press Warmup.
<<<
EXPECTED_BEHAVIOR: >>>
3 - Verify that the warmup button shows the progress of the warmup process.
<<<
RELATIONS:
- TYPE: Parent
  VALUE: RQ-H10TG-53
  ROLE: Verifies

[TEST_CASE]
UID: TC-H10TG-63
TITLE: Radiation Emission Control - Retrieve and Display Fault Information from Firmware - Test Case
STATEMENT: >>>
This test case verifies the user interface and user experience of the application by ensuring that, upon clicking the error indicator, the user is presented with detailed fault information when the device transitions to FAULT mode.
<<<
PREREQUISITES: >>>
1)Load a plan for treatment in the GBSK Internal unit.
<<<
STEPS: >>>
1. Log in to the External application. 

2. Navigate to the treatment view. 

3. Press the Prepare button to prepare the treatment. 

4. Press the Beam-On button to trigger emission delivery 

5. 

.Introduce a deliberate error in the firmware (e.g., trigger an e-stop interlock) . 

6. Click the Error indicator
<<<
EXPECTED_BEHAVIOR: >>>
Upon the user's clicking the error indicator, a pop-up view should be displayed presenting detailed fault information. 

This information shall include: 

• The type of fault occurrence. 

• The state in which the fault occurred. 

• A comparison of the expected versus the actual conditions that triggered the fault.
<<<
RELATIONS:
- TYPE: Parent
  VALUE: RQ-H10TG-284
  ROLE: Verifies

[TEST_CASE]
UID: TC-H10TG-115
TITLE: Treatment View - Record Emission Data Failure
STATEMENT: >>>
This test case verifies radiation emission control and safety. It validates that emission parameters are correctly managed and safety limits are enforced.
<<<
STEPS: >>>
1. Log in to the External application. 

2. Navigate to the treatment view. 

3. Press the Prepare button to prepare the treatment. 

4. Press the Beam-On button to trigger emission delivery. 

5. Interrupt the application's database connection during the emission.
<<<
EXPECTED_BEHAVIOR: >>>
5 - An error message should be displayed about the DB communication error during emission.
<<<
RELATIONS:
- TYPE: Parent
  VALUE: RQ-H10TG-22
  ROLE: Verifies

[TEST_CASE]
UID: TC-H10TG-108
TITLE: Quality Assurance - Perform System Safety Checks - Save Results
STATEMENT: >>>
This test case verifies the save functionality. It validates that data is properly persisted when save operations are executed.
<<<
STEPS: >>>
1. log in to the External application. 

2. Navigate to the Safety Checks tab in the Quality Assurance view. 

3. Change the toggle state of a few safety options ( e.g., X-ray light, X-ray sound) 

3. Press Save button 

4. toggle to Safety Checks report
<<<
EXPECTED_BEHAVIOR: >>>
4 - The safety Checks table shows the safety checks toggle state you have chosen and saved. 

4 - The date is the current date, and the performed-by shows the logged-in user.
<<<
RELATIONS:
- TYPE: Parent
  VALUE: RQ-H10TG-106
  ROLE: Verifies
- TYPE: Parent
  VALUE: RQ-H10TG-91
  ROLE: Verifies

[TEST_CASE]
UID: TC-H10TG-99
TITLE: Quality Assurance - System Safety Checks Reports - Test Case
STATEMENT: >>>
This test case is design to verify that the application provide the operator with an interface to display the history of test results which includes the following system safety features: X-Ray light, X-Ray sound, door interlock, e-stop, normal stop, live video stream, and live audio stream between the patient and operator.
<<<
PREREQUISITES: >>>
Perform System Safety Checks which includes the following system safety features: X-Ray light, X-Ray sound, door 
interlock, e-stop, normal stop, live video stream, and live audio stream between the patient and operator.
<<<
STEPS: >>>
1.Launch GBSK External 

2.Click the Quality Assurance tab 

3.Inside the Quality Assurance tab, click the Safety Checks tab.
<<<
EXPECTED_BEHAVIOR: >>>

The interface should display the history of test results which includes the following system safety features: X-Ray light, X-Ray sound, door 
interlock, e-stop, normal stop, live video stream, and live audio stream between the patient and operator.
<<<
RELATIONS:
- TYPE: Parent
  VALUE: RQ-H10TG-92
  ROLE: Verifies

[TEST_CASE]
UID: TC-H10TG-287
TITLE: Prevent a Treatment When There Is No Approved Physics Data
STATEMENT: >>>
This test case verifies that the system properly prevents or restricts certain operations. It validates that access control and business logic constraints are correctly enforced.
<<<
STEPS: >>>
1. Log in to the External application. 

2. Navigate to the treatment view. 

3. Press the Prepare button to prepare the treatment.
<<<
EXPECTED_BEHAVIOR: >>>
An error message appears, alerting the user that the treatment cannot be delivered without approved physics data.
<<<
RELATIONS:
- TYPE: Parent
  VALUE: RQ-H10TG-283
  ROLE: Verifies

[TEST_CASE]
UID: TC-H10TG-117
TITLE: Treatment View - Plan details view - DB communication error
STATEMENT: >>>
This test case verifies the handling of errors and faults in the system. It ensures appropriate responses to error conditions.
<<<
STEPS: >>>
1. Log in to the External application. 

2. Interrupt the application's database connection.

3. Navigate to the treatment view.
<<<
EXPECTED_BEHAVIOR: >>>
3 - An error message should be displayed about the DB communication error.
<<<
RELATIONS:
- TYPE: Parent
  VALUE: RQ-H10TG-8
  ROLE: Verifies

[TEST_CASE]
UID: TC-H10TG-140
TITLE: Treatment View - Safety Interlocks
STATEMENT: >>>
This test case verifies system safety checks and interlocks. It ensures that safety protocols are properly enforced and system safety constraints are maintained.
<<<
STEPS: >>>
1. Log in to the External application. 

2. Navigate to the treatment view. 

3. Press on the interlock button on the right button corner.
<<<
EXPECTED_BEHAVIOR: >>>
3 - Verify that all the following interlocks are visible: 

• Applicator 

• Remote Key 

• Door 

• Base E-Stop 

• Remote E-Stop 

• Timer #1 

• Timer #2 

• Water Level 

• Head 

• HVPS 

• Cooler Alarm 

• Watchdog 

• 

Ion pump
<<<
RELATIONS:
- TYPE: Parent
  VALUE: RQ-H10TG-139
  ROLE: Verifies

[TEST_CASE]
UID: TC-H10TG-129
TITLE: Treatment View - Prevent Treatment if the Daily Safety checks is not completed
STATEMENT: >>>
This test case verifies that the system properly prevents or restricts certain operations. It validates that access control and business logic constraints are correctly enforced.
<<<
STEPS: >>>
1. log in to the External application. 

2. Navigate to the treatment view. 

3. Press the Prepare button. 

4. Navigate to the Safety Checks tab in the Quality Assurance view. 

5. Save Quality checks with all toggles set to green. 

6. Navigate back to the treatment view. 

7. Press the Prepare button.
<<<
EXPECTED_BEHAVIOR: >>>
3 An alert message pops up, advising the user that the treatment is not enabled if the daily safety checks are not completed. 

7 - The Prepare process starts.
<<<
RELATIONS:
- TYPE: Parent
  VALUE: RQ-H10TG-96
  ROLE: Verifies

[TEST_CASE]
UID: TC-H10TG-109
TITLE: Treatment View - Audit user's actions
STATEMENT: >>>
This test case verifies that system actions are properly logged and audited. It validates that the audit trail accurately records user actions and data modifications.
<<<
STEPS: >>>
1. log in to the External application. 

2. Navigate to the treatment view. 

3. Press the Prepare button to prepare the treatment. 

4. Press the Beam-On button to trigger emission delivery. 

5. Press the Stop button to trigger stop emission.

6. Inspect the delivery outcome record, then repeat with a completed emission and a safely simulated delivery failure. Compare each record with measured delivery results, not just requested values.

7. Observe background telemetry and refreshes without triggering a user action.
<<<
EXPECTED_BEHAVIOR: >>>
3 - The action of preparation is shown in the log view. 

4 - The action of beaming on is shown in the log view. 

5 - The stop action is shown in the log view.

6. Each delivery outcome identifies the acting user and treatment context and distinguishes completion, cancellation, and failure using the measured result; an emission request alone is not recorded as completed delivery.

7. Background telemetry and RPC activity create no user-action records.
<<<
RELATIONS:
- TYPE: Parent
  VALUE: RQ-H10TG-89
  ROLE: Verifies

[TEST_CASE]
UID: TC-H10TG-290
TITLE: Physics View - Load collimator physics data
STATEMENT: >>>
This test case verifies the functionality and operation of Physics View. It validates that the component behaves according to specifications and system requirements.
<<<
PREREQUISITES: >>>
Use a controlled authoritative database containing applicator configurations A and B with distinct energies and presets. Give each preset distinct coil, correction-matrix, heater-current, output-factor, and reference-field values, and include intentionally different records under an unrelated preset. Keep access available to replace this data and to temporarily fail all physics-data reads.
<<<
STEPS: >>>
1. Log in to the External application.

2. Navigate to the Physics tab in the Quality Assurance view and press the Refresh icon.

3. Select applicator configuration A and its energy.

4. Observe the Applicator Size and Energy options, X Coil, Y Coil, Focus, and Heater Current. Capture the configuration-list responses from the database service.

5. In the authoritative database, change A's physics values, remove B, and add configuration C with a different energy and preset.

6. In the External Physics view, press the Refresh icon, then inspect the Applicator Size and Energy options.

7. Select the updated A and then C, observing the displayed physics values and the database service's configuration-list responses.

8. Make every physics-data read fail and press the Refresh icon.

9. Restore the database service and press the Refresh icon again.
<<<
EXPECTED_BEHAVIOR: >>>
2. The view publishes the complete A-and-B configuration snapshot after refresh; it does not expose a partially rebuilt list.

4. The displayed values equal A's authoritative values. Each preset, coil, correction-matrix, heater-current, output-factor, reference-field, and filtered-collimator response contains only records whose parent identifier matches its request; the unrelated preset's records are not used.

6. The refreshed options contain A and C, and stale configuration B is no longer selectable.

7. Updated A and C each display their own current authoritative physics values, with no stale values from the prior snapshot.

8. The application reports that the physics configuration could not be loaded. The log identifies each failed applicator configuration by identifier, type, and energy.

9. The retry succeeds and republishes the complete current A-and-C snapshot.
<<<
RELATIONS:
- TYPE: Parent
  VALUE: RQ-H10TG-280
  ROLE: Verifies

[TEST_CASE]
UID: TC-H10TG-147
TITLE: Treatment View - Perform System Warmup in COLD State
STATEMENT: >>>
This test case verifies the system warmup and initialization process. It validates that the system is properly prepared for operation and all parameters are initialized.
<<<
STEPS: >>>
1. Log in to the External application. 

2. Navigate to the Physics tab in Quality Assurance view. 

3. Select Plan parameters: ( e.g., Applicator Size: 1.5, Energy: 50, Duration: 60). 

4. Press Prepre 

5. Validate that System Status changes to Warmup and then becomes Ready at the end of the prepare ( after laoding phase) . VSetup 

6. Clear Plan 

7. Verify that the status becomes Primed. 

8. Press Prepare ( make sure that the status is still Primed) 

9. Observe System Status.
<<<
EXPECTED_BEHAVIOR: >>>
System status becomes HVSetup, without going through Warmup and Energy is ramped up.
<<<
RELATIONS:
- TYPE: Parent
  VALUE: RQ-H10TG-30
  ROLE: Verifies

[TEST_CASE]
UID: TC-H10TG-127
TITLE: Treatment View - Record Delivered Dose
STATEMENT: >>>
This test case verifies the functionality and operation of Treatment View. It validates that the component behaves according to specifications and system requirements.
<<<
STEPS: >>>
1. Log in to the External application. 

2. Navigate to the treatment view. 

3. Press the Prepare button to prepare the treatment. 

4. Press the Beam-On button to trigger emission delivery. 

5. Log in to the Internal application. 

6. Navigate to the Treatment tab in the Patient view. 

7.
<<<
EXPECTED_BEHAVIOR: >>>
The delivered dose is recorded and displayed in the table.
<<<
RELATIONS:
- TYPE: Parent
  VALUE: RQ-H10TG-21
  ROLE: Verifies

[TEST_CASE]
UID: TC-H10TG-291
TITLE: Allow Quality Checks with Dedicated Collimator only
STATEMENT: >>>
This test case verifies quality assurance checks and validations. It ensures that the system properly executes quality control procedures.
<<<
STEPS: >>>
1. Log in to the External application. 

2. Navigate to the Beam QA Checks tab in the Quality Assurance view.
<<<
EXPECTED_BEHAVIOR: >>>
A message should be displayed alerting the user that QC cannot be performed without a QC collimator.
<<<
RELATIONS:
- TYPE: Parent
  VALUE: RQ-H10TG-279
  ROLE: Verifies

[TEST_CASE]
UID: TC-H10TG-128
TITLE: Treatment View - Patient Monitoring
STATEMENT: >>>
This test case verifies system status and monitoring capabilities. It validates that system state information is accurately displayed and updated.
<<<
STEPS: >>>
1. Log in to the External application. 

2. Navigate to the treatment view. 

3. Press the Prepare button to prepare the treatment. 

4. Press the Beam-On button to trigger emission delivery.
<<<
EXPECTED_BEHAVIOR: >>>
4 - Verify that the camera shows the camera view located on the base of the device.
<<<
RELATIONS:
- TYPE: Parent
  VALUE: RQ-H10TG-86
  ROLE: Verifies

[TEST_CASE]
UID: TC-H10TG-50
TITLE: Treatment Console - Radiation Emission Control - Stop Emission - Test Case
STATEMENT: >>>
Verify that the application provides a stop control that allows the user to terminate radiation emissions immediately
<<<
PREREQUISITES: >>>
Load a plan for treatment in the GBSK Internal unit.
<<<
STEPS: >>>
1. Log in to the External application. 

2. Navigate to the treatment view. 

3. Press the Prepare button to prepare the treatment. 

4. Press the Beam-On button to trigger emission delivery. 

5. Press the Stop button to stop the emission. 

6. Click to approve the pop-up message indicating that the beaming has stopped.
<<<
EXPECTED_BEHAVIOR: >>>

6 - 

• The emission should stop. 

• The emission visual indicator should become gray. 

• The emission audible indicator should stop. 

• The timers should stop. 

• System status shall change to: Staged
<<<
RELATIONS:
- TYPE: Parent
  VALUE: RQ-H10TG-3
  ROLE: Verifies

[TEST_CASE]
UID: TC-H10TG-125
TITLE: Treatment View - Resume Prepare process after the error is cleared
STATEMENT: >>>
This test case verifies the handling of errors and faults in the system. It ensures appropriate responses to error conditions.
<<<
STEPS: >>>
1. Log in to the External application. 

2. Navigate to the treatment view. 

3. Press the Prepare button to prepare the treatment. 

4. Simulate a system error (e.g. activate interlock) 

5. Press clear error.
<<<
EXPECTED_BEHAVIOR: >>>
5 - After the error is cleared, the Prepare button can be re-triggered and complete the process.
<<<
RELATIONS:
- TYPE: Parent
  VALUE: RQ-H10TG-75
  ROLE: Verifies
- TYPE: Parent
  VALUE: RQ-H10TG-73
  ROLE: Verifies

[TEST_CASE]
UID: TC-H10TG-51
TITLE: Treatment Console - Radiation Emission Control - Emission visible indicator - Test Case
STATEMENT: >>>
This test case is designed to verify the presence and correct display of visual indicator in the interface during the emission process. It ensures that an amber-colored radiation icon is visible for the entire duration of emission, confirming the proper functioning of the UI layout element.
<<<
STEPS: >>>
1. Log in to the External application. 

2. Navigate to the treatment view. 

3. Press the Prepare button to prepare the treatment. 

4. Press the Beam-On button to trigger emission delivery.
<<<
EXPECTED_BEHAVIOR: >>>
There shall be a visible visual indicator in the interface for the entire duration of emission, appearing as an amber-colored radiation icon.
<<<
RELATIONS:
- TYPE: Parent
  VALUE: RQ-H10TG-5
  ROLE: Verifies

[TEST_CASE]
UID: TC-H10TG-123
TITLE: Treatment View - Treatment Fields Emission Progress indicators
STATEMENT: >>>
This test case verifies radiation emission control and safety. It validates that emission parameters are correctly managed and safety limits are enforced.
<<<
STEPS: >>>
1. Log in to the External application. 

2. Navigate to the treatment view. 

3. Press the Prepare button to prepare the treatment. 

4. Press the Beam-On button to trigger emission delivery.
<<<
EXPECTED_BEHAVIOR: >>>
4 - A visual indicator is displayed in the table to reflect the emission progress.
<<<
RELATIONS:
- TYPE: Parent
  VALUE: RQ-H10TG-95
  ROLE: Verifies
- TYPE: Parent
  VALUE: RQ-H10TG-10
  ROLE: Verifies
- TYPE: Parent
  VALUE: RQ-H10TG-4
  ROLE: Verifies

[TEST_CASE]
UID: TC-H10TG-61
TITLE: Radiation Emission Control - Record partial treatment - (After Two stoppings) - Test Case
STATEMENT: >>>
Verifying the layout for recording partial treatment, to ensure that the UI correctly displays the details of a partially completed treatment session after the emission is stopped prematurely twice.
<<<
PREREQUISITES: >>>
Create treatment field with duration of 12 Seconds and Load a plan for treatment in the GBSK Internal unit.
<<<
STEPS: >>>
1. Launch GBSK SW External. (The external unit should be located outside the treatment room).

2. Click the Prepare button.

3. Click the Beam On button.

4. After 5 seconds (check elapsed time), Click the Stop button (during the beaming process).

5. Repeat steps 3 and 4 (Click the Beam On button, and after 2 seconds, click the Stop button).
<<<
EXPECTED_BEHAVIOR: >>>
1 - The interface should display: System status: COLD, Button Label: Prepare

2 - The interface should display: System status: WARMUP, then PRIMED, then READY

3 - The button label should transition to "Launching", and subsequently to "Beaming on" with a progress bar.

4 - User shall receive an indicator or pop-up message indicating that the beaming has stopped. System status shall change to: READY.

5 - After stopping the emission at 5 seconds, restarting it, and then stopping it again after 2 seconds (out of total of 12 seconds), the stopped treatment field should appear in the treatment field view with Duration: 12, Remaining[sec]: 5. The remaining time should be specified with a resolution of 0.01 minutes (600msec) and marked as partial in the database.
<<<
RELATIONS:
- TYPE: Parent
  VALUE: RQ-H10TG-22
  ROLE: Verifies
- TYPE: Parent
  VALUE: RQ-H10TG-13
  ROLE: Verifies

[TEST_CASE]
UID: TC-H10TG-110
TITLE: Treatment View - Enable Loading a Treatment Plan -1
STATEMENT: >>>
The objective is to verify that the plan is loaded only in the staging GCB state.
<<<
STEPS: >>>
White box testing:

1. Open xcc solution in an IDE (Visual Studio or VSCode).

2. Search for the LoadPlan function.

3. Search for GcbStateNew.Staging state.

4. Search for SendOperationalPoint command which loads the plan into the GCB.
<<<
EXPECTED_BEHAVIOR: >>>
4 - The command should be sent only after the state is GcbStateNew.Staging.
<<<
RELATIONS:
- TYPE: Parent
  VALUE: RQ-H10TG-90
  ROLE: Verifies

[TEST_CASE]
UID: TC-H10TG-119
TITLE: Quality Assurance - Quality Checks Reports - Deviation
STATEMENT: >>>
The objective is to verify that the quality reports show the QC report in the form of a deviation from the referenced QC sample.
<<<
PREREQUISITES: >>>
Retrieve referenced QC sample result from DB.
<<<
STEPS: >>>
1. Log in to the External application.

2. Navigate to the Quality Checks tab in the Quality Assurance view.

3. Run QC process.

4. Toggle to the Quality Checks report.

5. Select the latest result performed.

6. Toggle to Row format.

7. Compare the row data to the referenced QC result.

8. Calculate the deviation.

9. Toggle to deviation format and compare results.
<<<
EXPECTED_BEHAVIOR: >>>
8 - The calculated deviations should be identical to the one presented in the report.
<<<
RELATIONS:
- TYPE: Parent
  VALUE: RQ-H10TG-94
  ROLE: Verifies
- TYPE: Parent
  VALUE: RQ-H10TG-93
  ROLE: Verifies

[TEST_CASE]
UID: TC-H10TG-134
TITLE: Quality Assurance - Allow Quality Checks with Dedicated Collimator only
STATEMENT: >>>
The objective is to verify that the operator cannot treat if the connected collimator is the QC collimator.
<<<
PREREQUISITES: >>>
A Plan is loaded from the Internal application.
<<<
STEPS: >>>
1. Log in to the External application.

2. Navigate to the treatment view.

3. Press the Prepare button to prepare the treatment.
<<<
EXPECTED_BEHAVIOR: >>>
3 - An alert message pops up alerting the user that the connected collimator mismatches the plan's collimator.
<<<
RELATIONS:
- TYPE: Parent
  VALUE: RQ-H10TG-279
  ROLE: Verifies

[TEST_CASE]
UID: TC-H10TG-146
TITLE: Treatment View - Treatment Plan Staging - 2
STATEMENT: >>>
The objective is to verify that the staging request has no operational-point count payload
and that its response contains a session ID.
<<<
STEPS: >>>
Automated test:

1. Run the GCB new-session command and response contract tests.
<<<
EXPECTED_BEHAVIOR: >>>
1. Verify the new-session request has zero payload words.
2. Verify the response contains the status and session ID only.
<<<
RELATIONS:
- TYPE: Parent
  VALUE: RQ-H10TG-31
  ROLE: Verifies

[TEST_CASE]
UID: TC-H10TG-297
TITLE: Device Information Version and Telemetry Selection
STATEMENT: >>>
Verify that System Information displays the release version reported by main control and
that telemetry-layout selection depends on the reported firmware mode rather than the
release version text.
<<<
PREREQUISITES: >>>
1. A GCB protocol fixture can provide valid 19-word device-information and telemetry packets.
<<<
STEPS: >>>
1. Start the external application with the fixture reporting a supported firmware mode and
   a known release version string.
2. Open System Information and record the main control board version.
3. Send valid telemetry and observe the Treatment view.
4. Change only the device-information release version string, then repeat the telemetry.
<<<
EXPECTED_BEHAVIOR: >>>
1. The device-information packet is accepted.
2. System Information displays the exact reported release version string.
3. The telemetry layout for the reported mode is selected and telemetry is displayed.
4. Telemetry remains accepted under the same mode after only the release version changes.
<<<
RELATIONS:
- TYPE: Parent
  VALUE: RQ-H10TG-286
  ROLE: Verifies
- TYPE: Parent
  VALUE: RQ-H10TG-2
  ROLE: Verifies

[[/SECTION]]

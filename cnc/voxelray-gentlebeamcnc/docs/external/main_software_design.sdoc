[DOCUMENT]
TITLE: GBSK Software Design Document for External GUI
UID: DHF-GBSK-0042
METADATA:
  COMPONENT: heracles-external-gui

[GRAMMAR]
IMPORT_FROM_FILE: @grammar

[[SECTION]]
TITLE: Purpose

[TEXT]
STATEMENT: >>>
The purpose of this document is to outline the design specifications of the GBSK External GUI Software.
<<<

[[/SECTION]]

[[SECTION]]
TITLE: Scope

[TEXT]
STATEMENT: >>>
This document describes the design modules and sub-modules of the GBSK External GUI Software. The information in this document is derived from the External GUI SRS, referenced in this document.

\*The term Software applies to both Software and Firmware components.
<<<

[[/SECTION]]

[[SECTION]]
TITLE: Abbreviations and Definitions

[TEXT]
STATEMENT: >>>
FW
Firmware

MCU
Microcontroller Unit

PRS
Product Requirements Specification

SDP
Software Development Plan

SRS
Software Requirements Specification

SW
Software
<<<

[[/SECTION]]

[[SECTION]]
TITLE: Overview

[TEXT]
STATEMENT: >>>
The external GUI console provides a means for the user to activate and monitor the treatment. It communicates with the main control board and treatment head camera.

The external GUI software runs on the external tablet console located outside the room.
<<<

[[/SECTION]]

[[SECTION]]
TITLE: References

[TEXT]
STATEMENT: >>>
Document ID / Reference Number: DHF-GBSK-0001, Rev. 1
Document TITLE: GBSK Software Development Plan (SDP)

Document ID / Reference Number: DHF-GBSK-0003, Rev. 1
Document TITLE: GBSK Software Verification Plan (SVP)

Document ID / Reference Number: DHF-GBSK-0007, Rev. 1
Document TITLE: GBSK External GUI Software Requirements Specification (SRS)

Document ID / Reference Number: DHF-GBSK-0004, Rev. 1
Document TITLE: GBSK Software Architecture Description
<<<

[[/SECTION]]

[[SECTION]]
TITLE: Architecture Overview

[TEXT]
STATEMENT: >>>
High Level System Architecture

.. image:: _assets/sds_arch_1.png

Main Modules

The design of the application is based on the MVVM pattern. There are three core components in the MVVM pattern: the model, the view, and the view model. Each serves a distinct purpose. The diagram below shows the relationships between the three components.

.. image:: _assets/sds_arch_2.png

The MVVN design pattern is implemented in the application as follows: the 4 th layer is the gRPC wrapper for communication with the database services.

.. image:: _assets/sds_arch_3.png
<<<

[[/SECTION]]

[[SECTION]]
PREFIX: SW-H10TG-
TITLE: Design Items

[DESIGN_ITEM]
UID: SW-H10TG-269
TITLE: A visual indication for system faults
STATEMENT: >>>
The GCB data store maintains an immutable list of the currently latched fault records and
publishes a fault-changed event whenever the list changes. The fault view renders each
record's category, formatted message, captured control-board state, and captured runtime.
The interlock pop-up also maps each record's formatted message to a false-state attention
row, which renders the red thumbs-down indicator. General fault-category flags continue
to drive the system-fault indication.
<<<
RELATIONS:
- TYPE: Parent
  VALUE: RQ-H10TG-284
  ROLE: Refines

[DESIGN_ITEM]
UID: SW-H10TG-255
TITLE: Beam On process
STATEMENT: >>>
The flow Beaming On (delivering emission) process should be implemented as described in the following chart diagram:

.. raw:: html

   <pre class="mermaid">
   graph TD
       A(["Plan loaded for treatment"]) --> B{"Plan can be executed"}
       
       B -- Yes --> C{"State = Startup / Cold / Primed"}
       B -- No ----> ShowError["Show plan error message"]
       
       C -- Yes --> Prepare["Left button: Prepare"]
       C -- No --> CheckStaged{"State = Staged"}
       
       CheckStaged -- Yes ----> CentralResume["Central button: Resume"]
       CheckStaged -- No ----> ShowError
       
       Prepare --> PressPrepare[/press Prepare/]
       PressPrepare --> StatePrimed{"State = Primed"}
       
       StatePrimed -- Yes --> LoadStage["Load and stage plan"]
       StatePrimed -- No --> WarmUp["WarmUp"] --> LoadStage
       
       LoadStage --> ConfirmRelease["Confirm and release plan"]
       ConfirmRelease --> HVSetup["HVPSCheck and HVSetup"]
       HVSetup --> StateReady["State = Ready<br>Central button: BeamOn"]
       
       StateReady --> PressBeamOn[/press BeamOn/]
       PressBeamOn --> StartEmission["Start emission"]
       
       StartEmission --> CheckInterrupt{"Fault or user interrupt"}
       
       CheckInterrupt -- No --> EmissionComplete["Emission complete"]
       EmissionComplete --> ResetTimers["Central button: ResetTimers"]
       ResetTimers --> EndNode([end])
       
       CheckInterrupt -- Yes --> CheckFault{"Fault state"}
       
       CheckFault -- Yes --> ClearErrors["Central button: ClearErrors"]
       ClearErrors --> PressClear[/press ClearErrors/]
       PressClear --> CentralResume
       
       CheckFault -- No --> CentralResume
       
       CentralResume --> PressResume[/press Resume/]
       PressResume --> ConfirmRelease
       
       ShowError --> EndNode
   </pre>
<<<
RELATIONS:
- TYPE: Parent
  VALUE: RQ-H10TG-9
  ROLE: Refines
- TYPE: Parent
  VALUE: RQ-H10TG-43
  ROLE: Refines
- TYPE: Parent
  VALUE: RQ-H10TG-73
  ROLE: Refines

[DESIGN_ITEM]
UID: SW-H10TG-271
TITLE: Clear Fault Flags
STATEMENT: >>>
The fault view sends the clear command through the main-board model and unified GCB command
interface. The firmware acknowledges the command, clears its latched records, increments
the clear epoch, and publishes an empty fault update. The telemetry processor applies that
update to the GCB data store, which notifies the fault view.

.. raw:: html

    <pre class="mermaid">
    sequenceDiagram
        participant FaultsViewModel
        participant MainBoardModel
        participant GcbCommandInterface
        participant Firmware
        participant SystemTelemetryProcessor
        participant GCBDataStore

        FaultsViewModel->>MainBoardModel: ClearFaults
        MainBoardModel->>GcbCommandInterface: ClearFaults
        GcbCommandInterface->>Firmware: [UDP] clear-fault directive
        Firmware-->>GcbCommandInterface: [UDP] command response
        Firmware-->>SystemTelemetryProcessor: [UDP] empty fault update, new clear epoch
        SystemTelemetryProcessor->>GCBDataStore: ApplyFaultUpdate
        GCBDataStore-->>FaultsViewModel: FaultsChangedEvent(empty)
    </pre>
<<<
RELATIONS:
- TYPE: Parent
  VALUE: RQ-H10TG-284
  ROLE: Refines

[DESIGN_ITEM]
UID: SW-H10TG-249
TITLE: Confirmation of Treatment Plan
STATEMENT: >>>
.. raw:: html

   <pre class="mermaid">
   sequenceDiagram
       autonumber
       
       box Application
           participant MainBoardModel
       end
       box ControlBoard
           participant Firmware
       end

       Note over MainBoardModel, Firmware: Board is in Staged state
       
       activate MainBoardModel
       MainBoardModel->>Firmware: "[UDP] confirm scalar operational parameters"
       activate Firmware
       Firmware-->>MainBoardModel: "[UDP] status response"
       deactivate Firmware

       MainBoardModel->>Firmware: "[UDP] ReleasePlan command"
       activate Firmware
       Firmware-->>MainBoardModel: "[UDP] status response"
       deactivate Firmware

       Note over MainBoardModel: wait for Ready board state
       MainBoardModel->>MainBoardModel: 
       deactivate MainBoardModel
   </pre>
<<<
RELATIONS:
- TYPE: Parent
  VALUE: RQ-H10TG-35
  ROLE: Refines

[DESIGN_ITEM]
UID: SW-H10TG-264
TITLE: Daily Warmup Process
STATEMENT: >>>
The flow for performing Daily Warmup should be implemented as described in the following sequence diagram:

The external configurations provide the configured targets for fast warmup and conditioning.
Before sending either command, the application validates the configured target. If a
warmup command receives an access-error status, the command interface raises an error
explaining that warmup cannot start in the current state and that both e-stops must be
released. The view model logs and displays the failure rather than recording completion.

.. raw:: html

   <pre class="mermaid">
   sequenceDiagram
       autonumber
       
       box Application
           participant DailyWarmUpViewModel
           participant MainBoardModel
           participant WarmupModel
       end
       box ControlBoard
           participant Firmware
       end
       box Database
           participant WarmupService
       end

       Note over DailyWarmUpViewModel, WarmupService: User initiates Warmup/Conditioning
       
       DailyWarmUpViewModel->>MainBoardModel: WarmUp
       activate DailyWarmUpViewModel
       activate MainBoardModel
       
       Note over MainBoardModel: check target filament current range
       MainBoardModel->>MainBoardModel: 

       alt "[Startup board state]"
           MainBoardModel->>Firmware: "[UDP] initialization command"
           activate Firmware
           Note over Firmware: initialize
           Firmware->>Firmware: 
           Firmware-->>MainBoardModel: "[UDP] status response"
           deactivate Firmware
           
           Note over MainBoardModel: wait for Cold state in the telemetry
           MainBoardModel->>MainBoardModel: 
       end

       MainBoardModel->>Firmware: "[UDP] Warmup/Conditioning command"
       activate Firmware
       Note over Firmware: start warming up
       Firmware->>Firmware: 
       Firmware-->>MainBoardModel: "[UDP] status response"
       deactivate Firmware

       Note over MainBoardModel: wait for Warmup/Conditioning terminal state
       MainBoardModel->>MainBoardModel: 

       MainBoardModel-->>DailyWarmUpViewModel: 
       deactivate MainBoardModel
       
       DailyWarmUpViewModel->>WarmupModel: Save Warmup/Conditioning event
       activate WarmupModel
       
       WarmupModel->>WarmupService: grpc: Save Warmup event
       activate WarmupService
       Note over WarmupService: create a DB record
       WarmupService->>WarmupService: 
       WarmupService-->>WarmupModel: stored record
       deactivate WarmupService
       
       Note over WarmupModel: add record to the list
       WarmupModel->>WarmupModel: 
       WarmupModel-->>DailyWarmUpViewModel: 
       deactivate WarmupModel
       deactivate DailyWarmUpViewModel
   </pre>
<<<
RELATIONS:
- TYPE: Parent
  VALUE: RQ-H10TG-1
  ROLE: Refines
- TYPE: Parent
  VALUE: RQ-H10TG-29
  ROLE: Refines
- TYPE: Parent
  VALUE: RQ-H10TG-30
  ROLE: Refines

[DESIGN_ITEM]
UID: SW-H10TG-265
TITLE: Display System Telemetry
STATEMENT: >>>
The receive-only telemetry service listens for unsolicited GCB datagrams. Device-information
packets identify the firmware mode; the system telemetry processor selects the corresponding
parser. Unsupported modes and malformed packets are rejected without replacing the last
valid state.

Each parser translates the physical interlock bits once into the shared ``SystemInterlock``
identity space. ``SystemInterlocks`` retains the raw status and required masks for service
diagnostics and exposes semantic availability, state, and required-state queries to the
application. Valid immutable snapshots are published at most every 250 ms. If no valid
telemetry is received for 1.5 seconds, the processor publishes an unavailable snapshot.

.. raw:: html

    <pre class="mermaid">
    sequenceDiagram
        participant TelemetryView
        participant GCBDataStore
        participant MainBoardModel
        participant SystemTelemetryProcessor
        participant TelemetryService
        participant Firmware

        Firmware->>TelemetryService: [UDP] device information, 1 Hz
        TelemetryService->>SystemTelemetryProcessor: Select parser by firmware mode
        Firmware->>TelemetryService: [UDP] system telemetry, 100 Hz
        TelemetryService->>SystemTelemetryProcessor: Process datagram
        SystemTelemetryProcessor->>MainBoardModel: OnSystemTelemetryChanged(ISystemTelemetry?)
        MainBoardModel->>GCBDataStore: Set immutable SystemTelemetry
        GCBDataStore-->>TelemetryView: Publish semantic telemetry
    </pre>
<<<
RELATIONS:
- TYPE: Parent
  VALUE: RQ-H10TG-2
  ROLE: Refines
- TYPE: Parent
  VALUE: RQ-H10TG-82
  ROLE: Refines

[DESIGN_ITEM]
UID: SW-H10TG-6
TITLE: EMR: Treatment Console - Load For Treatment Plan Flow
STATEMENT: >>>
The treatment console application shall be triggered by the base (internal) application with a treatment plan to be delivered. When the application is triggered, the patient details, plan details, and treatment fields should be displayed, and the plan should be ready for activation.

The following sequence diagram describes the workflow of LoadForTreatment flow (should be moved to detailed design)

.. raw:: html

   <pre class="mermaid">
   sequenceDiagram
       autonumber
       actor User
       participant CC
       participant Moses
       participant DB
       participant TC

       User->>CC: LoadForTreatment
       activate CC
       CC->>Moses: LoadForTreatment
       activate Moses
       Moses->>DB: UpdatePlanTreatmentState(Pending)
       activate DB
       DB->>TC: LoadForTreatment Event
       activate TC
       TC->>Moses: UpdatePlanTreatmentState(Loaded)
       Moses->>DB: UpdatePlanTreatmentState(Loaded)
       DB->>CC: PlanLoaded Event
       activate CC
       deactivate CC
       deactivate TC
       deactivate DB
       deactivate Moses
       deactivate CC
   </pre>

1. The user presses the LoadForTreatment buttoning the Base UI.
2. C&C sends LoadForTreatment API to Moses.
3. Moses (DB Service) fetches all Pending plans from DB.

4. If there are no Pending plans, Moses changes the plan state to Pending
5. Moses triggers LoadForTreatment Event with patient details, plan, and treatment fields
6. Treatment Console (external) receives the event and loads the plan into the UI.
7. Treatment Console sends TreatmentLoaded API
8. Treatment Console locks the treatment view.
9. Moses changes the plan state to Loaded
10. Moses trigger the TreatmentLoaded event to the C&C
11. C&C locks the plan view.
<<<
RELATIONS:
- TYPE: Parent
  VALUE: RQ-H10TG-32
  ROLE: Refines

[DESIGN_ITEM]
UID: SW-H10TG-266
TITLE: Emission visible indicator
STATEMENT: >>>
A glowing radiation icon with an Amber color will provide a visual indication of X-ray emission.

.. image:: _assets/SW-H10TG-266.png
<<<
RELATIONS:
- TYPE: Parent
  VALUE: RQ-H10TG-5
  ROLE: Refines

[DESIGN_ITEM]
UID: SW-H10TG-253
TITLE: Enable window switching after emission delivery
STATEMENT: >>>
.. raw:: html

   <pre class="mermaid">
   sequenceDiagram
       autonumber
       actor User
       
       box Application
           participant OperatePlanViewModelBase
           participant MainBoardModel
           participant UIStateMachine
           participant TabControl
       end

       Note over OperatePlanViewModelBase, TabControl: "Plan is loaded and confirmed, Board is in Ready state"
       
       alt "[Emission]"
           User->>OperatePlanViewModelBase: BeamOn
           activate OperatePlanViewModelBase
           OperatePlanViewModelBase->>MainBoardModel: BeamOn
           activate MainBoardModel
           Note over MainBoardModel: command HW to start emission
           MainBoardModel->>MainBoardModel: 
           Note over MainBoardModel: "wait for Staged state"
           MainBoardModel->>MainBoardModel: 
           
           MainBoardModel-->>OperatePlanViewModelBase: BeamOn task result
           deactivate MainBoardModel
           OperatePlanViewModelBase->>User: "ClearPlan?"
           deactivate OperatePlanViewModelBase
       end

       User->>OperatePlanViewModelBase: ClearPlan
       activate OperatePlanViewModelBase
       OperatePlanViewModelBase->>MainBoardModel: ClearPlan
       activate MainBoardModel
       Note over MainBoardModel: command HW to clear plan
       MainBoardModel->>MainBoardModel: 
       Note over MainBoardModel: "wait for Primed state"
       MainBoardModel->>MainBoardModel: 
       
       MainBoardModel-->>OperatePlanViewModelBase: ClearPlan task result
       deactivate MainBoardModel

       OperatePlanViewModelBase->>UIStateMachine: unlock tabs
       activate UIStateMachine
       UIStateMachine->>TabControl: notify on lock flag change
       activate TabControl
       Note over TabControl: enable tab switch
       TabControl->>TabControl: 
       TabControl-->>UIStateMachine: 
       deactivate TabControl
       UIStateMachine-->>OperatePlanViewModelBase: 
       deactivate UIStateMachine
       deactivate OperatePlanViewModelBase
   </pre>
<<<
RELATIONS:
- TYPE: Parent
  VALUE: RQ-H10TG-52
  ROLE: Refines

[DESIGN_ITEM]
UID: SW-H10TG-277
TITLE: Get Interlocks state
STATEMENT: >>>
The interlock dialog view model derives ``SystemIsReady`` from the latest immutable
telemetry snapshot, the attached applicator, the registered applicator collection, and the
treatment-plan applicator configuration. Readiness requires a clear buffered master-fault
input, no active system fault, every required interlock to be available and active, and a
ready applicator check.

The view model publishes four operator-facing groups: E-stops, Door closed, Keys, and one
Applicator row. It first treats a missing attached applicator as ``No applicator``; then an
attached serial absent from the registered collection as ``Unknown applicator``; then a
registered applicator whose configuration differs from the treatment plan as ``Incorrect
applicator``. Otherwise the row is ``Applicator`` with the existing green thumbs-up state.
This ordered evaluation is shared by both interlock view models, so any error makes
``SystemIsReady`` false and exactly one applicator row is displayed.

E-stop and key groups aggregate their base and remote inputs and disclose their
individual child rows only while the group is not ready or is unavailable.

Other physical inputs are aggregated into operator-facing subsystem names. The Auxiliary
safety circuit group contains spare interlocks 1 and 2. Only groups with a false state
enter the attention collection. The buffered master-fault state enters that collection
as Master fault only when it is false and every other available interlock is ready.
Unavailable technical signals are not reported as bad.

``FaultsChangedEvent`` snapshots rebuild one false-state attention row per active
``FaultEntry.Message``. The inherited ``ForegroundDefaultBrush`` on the pop-up root keeps
body and row text consistent with the prior gray interlock-dialog styling while section
headings retain ``AccentForegroundColor``. ``ShowClearFaultsButton`` additionally checks
``IHeraclesExternalSettings`` and becomes true when the buffered master-fault input is bad,
the telemetry fault mask is nonzero, or the active fault list is nonempty. The fixed
bottom Clear Errors button reuses the existing refresh-plus-cancel icon treatment, invokes
``IMainBoardAPI.ClearFaults``, and reports command failures through
``IPopUpService``. The same button remains collapsed in the Internal GUI.

.. raw:: html

    <pre class="mermaid">
    sequenceDiagram
        participant InterlocksDialog
        participant InterlocksDialogViewModel
        participant GCBDataStore
        participant SystemInterlocks
        participant MainBoardAPI

        GCBDataStore-->>InterlocksDialogViewModel: SystemTelemetryChangedEvent
        GCBDataStore-->>InterlocksDialogViewModel: FaultsChangedEvent
        InterlocksDialogViewModel->>SystemInterlocks: derive readiness and grouped states
        SystemInterlocks-->>InterlocksDialogViewModel: tri-state semantic values
        InterlocksDialogViewModel-->>InterlocksDialog: readiness, operator checks, bad groups, fault messages, clear visibility
        InterlocksDialog-->>InterlocksDialog: disclose failed e-stop and key children
        InterlocksDialog->>InterlocksDialogViewModel: ClearFaultsCommand [External GUI only]
        InterlocksDialogViewModel->>MainBoardAPI: ClearFaults
    </pre>
<<<
RELATIONS:
- TYPE: Parent
  VALUE: RQ-H10TG-139
  ROLE: Refines

[DESIGN_ITEM]
UID: SW-H10TG-258
TITLE: Initialize the System
STATEMENT: >>>
.. raw:: html

   <pre class="mermaid">
   sequenceDiagram
       autonumber
       
       box Application
           participant OperatePlanViewModelBase
           participant MainBoardModel
           participant WarmupModel
       end
       box ControlBoard
           participant Firmware
       end
       box Database
           participant WarmupService
       end

       Note over OperatePlanViewModelBase, WarmupService: "User Initiates Warmup/Conditioning"
       
       OperatePlanViewModelBase->>MainBoardModel: WarmUp
       activate OperatePlanViewModelBase
       activate MainBoardModel
       
       Note over MainBoardModel: check target filament current range
       MainBoardModel->>MainBoardModel: 

       alt "[Startup board state]"
           MainBoardModel->>Firmware: "[UDP] initialization command"
           activate Firmware
           Note over Firmware: initialize
           Firmware->>Firmware: 
           Firmware-->>MainBoardModel: "[UDP] status response"
           deactivate Firmware
           
           Note over MainBoardModel: "wait for Cold state in the telemetry"
           MainBoardModel->>MainBoardModel: 
       end

       MainBoardModel->>Firmware: "[UDP] Warmup/Conditioning command"
       activate Firmware
       Note over Firmware: start warming up
       Firmware->>Firmware: 
       Firmware-->>MainBoardModel: "[UDP] status response"
       deactivate Firmware

       Note over MainBoardModel: "wait for Warmup/Conditioning terminal state"
       MainBoardModel->>MainBoardModel: 

       MainBoardModel->>WarmupModel: "Save Warmup/Conditioning event"
       activate WarmupModel
       
       WarmupModel->>WarmupService: "grpc: Save Warmup event"
       activate WarmupService
       Note over WarmupService: create a DB record
       WarmupService->>WarmupService: 
       WarmupService-->>WarmupModel: stored record
       deactivate WarmupService
       
       Note over WarmupModel: add record to the list
       WarmupModel->>WarmupModel: 
       WarmupModel-->>MainBoardModel: 
       deactivate WarmupModel
       
       MainBoardModel-->>OperatePlanViewModelBase: 
       deactivate MainBoardModel
       deactivate OperatePlanViewModelBase
   </pre>
<<<
RELATIONS:
- TYPE: Parent
  VALUE: RQ-H10TG-26
  ROLE: Refines
- TYPE: Parent
  VALUE: RQ-H10TG-29
  ROLE: Refines
- TYPE: Parent
  VALUE: RQ-H10TG-30
  ROLE: Refines
- TYPE: Parent
  VALUE: RQ-H10TG-57
  ROLE: Refines

[DESIGN_ITEM]
UID: SW-H10TG-275
TITLE: Live Monitoring Camera Integration
STATEMENT: >>>
.. raw:: html

    <pre class="mermaid">
    sequenceDiagram
        participant Control as :VideoLiveFeedControl
        participant WebView2
        participant go2rtc

        Application ->> Control: Load
        activate Control
        Control->>Control: InitializeAllCameras
        activate Control
        deactivate Control
        Control->>WebView2: Navigate to go2rtc
        activate WebView2
        WebView2->>go2rtc: WebRTC Connect
        go2rtc-->>WebView2: Video + Audio
        deactivate WebView2
        deactivate Control
    </pre>
<<<
RELATIONS:
- TYPE: Parent
  VALUE: RQ-H10TG-86
  ROLE: Refines

[DESIGN_ITEM]
UID: SW-H10TG-272
TITLE: LogService module
STATEMENT: >>>
The action audit service records explicit preparation, Beam On, and Stop commands with the acting user and treatment identifiers. Delivery outcome records use measured emission results and distinguish completed, cancelled, and failed delivery from the requested emission. Background telemetry, automatic refreshes, and low-level RPC activity do not create user-action records.

.. image:: _assets/SW-H10TG-272.png
<<<
RELATIONS:
- TYPE: Parent
  VALUE: RQ-H10TG-89
  ROLE: Refines

[DESIGN_ITEM]
UID: SW-H10TG-259
TITLE: Perform Quality Checks
STATEMENT: >>>
The external application routes QC-board ping and acquisition commands through
``GcbCommandInterface`` and main control. The start request is exactly ``[1, 0]`` and must return
Armed before Beam On is sent. The stop request is exactly ``[2, 0]``. Stop polls Starting,
Accumulating, or Stopping responses within one shared two-second deadline; Complete returns the
unsigned channel 0 sum, channel 1 sum, channel 0 sample count, channel 1 sample count, and numeric
session status. Error or deadline expiry fails the acquisition.

``QcReadings`` retains its immutable two-channel wire result. Channel 0 carries the single analog
diode acquisition; channel 1 remains present for compatibility and is zero and disconnected.
Reports persist exactly the two accumulation values while retaining each channel's independent
sample count as metadata. Normal GCB telemetry exposes both wire channels' accumulations,
instantaneous readings, and ADC connection states. UCSI identifies all QC values in counts, records
schema version 2 with the two accumulation columns, and reads schema version 1 recordings with
those fields represented as null.

The flow for performing Daily Quality Checks is:

.. raw:: html

   <pre class="mermaid">
   sequenceDiagram
       autonumber
       actor User

       box Application
           participant QualityCheckViewModel
           participant MainBoardModel
           participant GcbQcbService
           participant GcbCommandInterface
           participant QcReportService
       end
       box Control system
           participant MainControl
           participant QcDetector
       end

       Note over QualityCheckViewModel: build the list of calibrated QA emissions
       User->>QualityCheckViewModel: select energy and exactly one emission

       User->>QualityCheckViewModel: Prepare
       activate QualityCheckViewModel
       QualityCheckViewModel->>GcbQcbService: PingBoardAsync
       GcbQcbService->>GcbCommandInterface: PingQcb
       GcbCommandInterface->>MainControl: [UDP] QC-board ping
       MainControl->>QcDetector: check connection
       QcDetector-->>MainControl: connection status
       MainControl-->>GcbCommandInterface: validated ping response
       GcbCommandInterface-->>GcbQcbService: connection status
       GcbQcbService-->>QualityCheckViewModel: connection status
       alt detector is unavailable
           QualityCheckViewModel-->>User: return to StandBy and display preparation error
       else detector is available
           QualityCheckViewModel->>MainBoardModel: load selected emission
           MainBoardModel-->>QualityCheckViewModel: selected emission confirmed
           QualityCheckViewModel-->>User: enable Beam On
       end
       deactivate QualityCheckViewModel

       User->>QualityCheckViewModel: Beam On
       activate QualityCheckViewModel
       QualityCheckViewModel->>GcbQcbService: start detector acquisition
       GcbQcbService->>GcbCommandInterface: StartQcbReadings
       GcbCommandInterface->>MainControl: [UDP] [Start, 0]
       MainControl->>QcDetector: command Accumulating and wait for Active
       QcDetector-->>MainControl: Active
       MainControl-->>GcbCommandInterface: Armed
       GcbCommandInterface-->>GcbQcbService: start accepted
       GcbQcbService-->>QualityCheckViewModel: start accepted
       QualityCheckViewModel->>MainBoardModel: Beam On selected emission
       MainBoardModel-->>QualityCheckViewModel: emission entered
       QualityCheckViewModel->>GcbQcbService: stop readings
       GcbQcbService->>GcbCommandInterface: StopQcbReadings
       loop shared two-second deadline
           GcbCommandInterface->>MainControl: [UDP] [Stop, 0]
           MainControl-->>GcbCommandInterface: sums, counts, session status
       end
       GcbCommandInterface-->>GcbQcbService: immutable two-channel QcReadings
       GcbQcbService-->>QualityCheckViewModel: selected-emission readings
       alt acquisition failed or timed out
           QualityCheckViewModel->>GcbQcbService: one best-effort Stop
           QualityCheckViewModel->>MainBoardModel: Stop
           QualityCheckViewModel-->>User: display acquisition error
       else acquisition completed
           MainBoardModel-->>QualityCheckViewModel: selected emission completed
           QualityCheckViewModel->>MainBoardModel: reset timers and clear plan
           QualityCheckViewModel->>QcReportService: save selected emission and two channel sums
           QcReportService-->>QualityCheckViewModel: report saved
           Note over QualityCheckViewModel: return to StandBy and clear selection
           QualityCheckViewModel-->>User: selected emission completed
       end
       deactivate QualityCheckViewModel
   </pre>
<<<
RELATIONS:
- TYPE: Parent
  VALUE: RQ-H10TG-66
  ROLE: Refines
- TYPE: Parent
  VALUE: RQ-H10TG-280
  ROLE: Refines

[DESIGN_ITEM]
UID: SW-H10TG-282
TITLE: Authoritative Physics Configuration Synchronization
STATEMENT: >>>
``CollimatorService`` first fetches the active head, the complete collimator-configuration list, and the collimators. It then calls ``CollimatorModel.Reset`` once with all three results. Reset links each collimator to the configuration identified by its foreign key, replaces both observable collections, and raises the configuration-change notification only after the complete snapshot is available. Consumers therefore do not observe a partially rebuilt configuration list.

The database list services enforce the request's parent identifier when reading the hierarchy: presets are filtered by collimator-configuration identifier; coils, correction matrices, heater-current configurations, output factors, and reference fields are filtered by preset identifier; and an optional collimator-configuration identifier filters collimators. Rows belonging to another parent are never returned as part of the requested configuration.

The Physics view responds to the complete configuration-change notification by rebuilding its selectable applicator and energy options and forcing a refresh of their physics data. Refreshes are serialized. A successful refresh replaces the physics-data store so entries absent from the authoritative snapshot are removed. A failed configuration read is logged with its identifier, type, and energy; when every requested configuration fails, the refresh reports an error and remains retryable.
<<<
RELATIONS:
- TYPE: Parent
  VALUE: RQ-H10TG-280
  ROLE: Refines

[DESIGN_ITEM]
UID: SW-H10TG-260
TITLE: Perform System Safety Checks
STATEMENT: >>>
The flow for performing System Safety Checks should be implemented as described in the following sequence diagram:

.. raw:: html

   <pre class="mermaid">
   sequenceDiagram
       autonumber
       actor User
       
       box Application
           participant SafetyCheckViewModel
           participant SafetyCheckModel
           participant MainBoardModel
       end
       box Database
           participant SafetyCheckService
       end

       SafetyCheckViewModel->>SafetyCheckModel: fetch SafetyCheck reports
       activate SafetyCheckViewModel
       activate SafetyCheckModel
       SafetyCheckModel->>SafetyCheckService: grpc: read report list
       activate SafetyCheckService
       SafetyCheckService-->>SafetyCheckModel: grpc: stored reports
       deactivate SafetyCheckService
       SafetyCheckModel-->>SafetyCheckViewModel: 
       deactivate SafetyCheckModel

       alt "[SafetyCheck is allowed with current collimator type]"
           Note over SafetyCheckViewModel: prepare one scalar SafetyCheck emission
           SafetyCheckViewModel->>SafetyCheckViewModel: 
           Note over SafetyCheckViewModel: enable Prepare button
           
           User->>SafetyCheckViewModel: Prepare
           SafetyCheckViewModel->>MainBoardModel: load scalar emission
           activate MainBoardModel
           
           Note over MainBoardModel: send scalar point and confirmation to ControlBoard
           MainBoardModel->>MainBoardModel: 
           Note over MainBoardModel: wait for Ready state
           MainBoardModel->>MainBoardModel: 
           
           MainBoardModel-->>SafetyCheckViewModel: task status
           deactivate MainBoardModel
           Note over SafetyCheckViewModel: enable BeamOn button
           
           loop "[User starts/stops/resumes emission]"
               Note over SafetyCheckViewModel: make checks one by one
               SafetyCheckViewModel->>SafetyCheckViewModel: 
               Note over SafetyCheckViewModel: toggle check UI controls
           end
           
           User->>SafetyCheckViewModel: save SafetyCheck report
           SafetyCheckViewModel->>SafetyCheckModel: add new record
           activate SafetyCheckModel
           
           SafetyCheckModel->>SafetyCheckService: create new record
           activate SafetyCheckService
           SafetyCheckService-->>SafetyCheckModel: stored record
           deactivate SafetyCheckService
           
           Note over SafetyCheckModel: add record to the list
           SafetyCheckModel->>SafetyCheckModel: 
           SafetyCheckModel-->>SafetyCheckViewModel: 
           deactivate SafetyCheckModel
           
           SafetyCheckViewModel->>MainBoardModel: clear plan
           activate MainBoardModel
           Note over MainBoardModel: send ResetTimers/ClearPlan commands to ControlBoard
           MainBoardModel->>MainBoardModel: 
           MainBoardModel-->>SafetyCheckViewModel: task status
           deactivate MainBoardModel
           
           Note over SafetyCheckViewModel: navigate to SafetyCheck reports view
           SafetyCheckViewModel->>SafetyCheckViewModel: 
           SafetyCheckViewModel-->>User: 
       end
       deactivate SafetyCheckViewModel
   </pre>
<<<
RELATIONS:
- TYPE: Parent
  VALUE: RQ-H10TG-91
  ROLE: Refines
- TYPE: Parent
  VALUE: RQ-H10TG-92
  ROLE: Refines
- TYPE: Parent
  VALUE: RQ-H10TG-106
  ROLE: Refines

[DESIGN_ITEM]
UID: SW-H10TG-267
TITLE: Plan Details Layout
STATEMENT: >>>
The application shall provide an interface allowing the operator to view the treatment plan details with the following parameters:

.. image:: _assets/SW-H10TG-267.png
<<<
RELATIONS:
- TYPE: Parent
  VALUE: RQ-H10TG-8
  ROLE: Refines

[DESIGN_ITEM]
UID: SW-H10TG-278
TITLE: Play sound during emission
STATEMENT: >>>
The flow for providing audible indication during active emission should be implemented as described in the following sequence diagram:

.. raw:: html

    <pre class="mermaid">
    sequenceDiagram
        box Application
            participant MainView
            participant Converter as GcbStatusToRadiation<br/>HazardActiveStateConverter
            participant GCBDataStore
        end
        box Control Board
            participant Firmware
        end

        [?] ->> MainView: OnLoad
        activate MainView
        
        MainView->>GCBDataStore: getSystemTelemetry
        activate GCBDataStore
        
        activate Firmware
        Firmware-->>GCBDataStore: OnTelemetryChanged
        deactivate Firmware
        
        GCBDataStore-->>MainView: return SystemTelemetry
        deactivate GCBDataStore

        MainView->>Converter: convert
        activate Converter
        Converter->>Converter: if emission return else return false
        activate Converter
        deactivate Converter
        Converter->>MainView: return state
        deactivate Converter

        MainView->>MainView: ChangeRadiationIconColor(state)
        activate MainView
        deactivate MainView
        
        MainView->>MainView: PlaySound(state)
        activate MainView
        deactivate MainView
        
        deactivate MainView
    </pre>
<<<
RELATIONS:
- TYPE: Parent
  VALUE: RQ-H10TG-87
  ROLE: Refines

[DESIGN_ITEM]
UID: SW-H10TG-262
TITLE: Prevent Treatment if the Daily Safety checks is not completed
STATEMENT: >>>
The flow for Prevent Treatment when no daily safety checks are performed should be implemented as described in the following flow chart diagram:

.. raw:: html

   <pre class="mermaid">
   graph TD
       A(["Ready for Prepare"]) --> B[/press Prepare/]
       B --> C{"Daily SafetyCheck is done?"}
       
       C -- Yes --> D{"Is it complete?"}
       C -- No ----> ShowError["Show error, block treatment"]
       
       D -- Yes ----> ProceedPrepare["Proceed with Prepare"]
       D -- No --> E{"Door interlock, e-stop,<br>normal stop checks passed?"}
       
       E -- Yes --> Alert[/Safety alert:<br>ask for confirmation/]
       E -- No --> ShowError
       
       Alert --> F{"Proceed treatment?"}
       
       F -- Yes --> ProceedPrepare
       F -- No ----> EndNode([end])
       
       ProceedPrepare --> EndNode
       ShowError --> EndNode
   </pre>
<<<
RELATIONS:
- TYPE: Parent
  VALUE: RQ-H10TG-96
  ROLE: Refines
- TYPE: Parent
  VALUE: RQ-H10TG-97
  ROLE: Refines
- TYPE: Parent
  VALUE: RQ-H10TG-283
  ROLE: Refines

[DESIGN_ITEM]
UID: SW-H10TG-281
TITLE: QC Result Persistence, Acceptance, and Approval
STATEMENT: >>>
``QcReportService`` creates one ``QcSampleHeader`` per collimator configuration with the
current creation time and the authorized operator's email address. ``QcRepository`` persists
that header, its QA-emission fields, and each field's diode intensities as a parent-child
hierarchy. The SQLite gRPC repositories preserve the creation timestamps and parent identifiers
and filter samples by collimator configuration, fields by sample, and intensities by field.
When opening an existing table, the repository backfills an empty indexed parent identifier
from the serialized record before serving the filtered reads.

``QcTreatmentAcceptanceService`` orders the selected configuration's samples by creation time
and identifier, uses the newest sample and newest referenced sample, and returns:

* ``Missing`` when the newest sample does not exist or is older than 24 hours;
* ``Accepted`` immediately when the newest sample has a persisted approver;
* ``NoReference`` when an unapproved current sample has no reference;
* otherwise, ``Accepted`` only when the two samples have the same non-empty ordered field and
  value shape and every value's absolute deviation is less than 3 percent; all other cases
  return ``Failed``.

Deviation calculation returns zero for a zero value against a zero reference. A nonzero value
against zero, a null value, a missing field, or a mismatched value count cannot pass acceptance.

``QCSampleService`` authenticates an approval request against the persisted users before
loading or updating the sample. Username matching is case-insensitive and the supplied password
must match and the persisted failed-login count must be below 10. Authentication failure returns
``Unauthenticated`` without modifying the sample; success stores the authenticated user's email
address in ``ApprovedBy``. These approval checks neither increment nor reset the failed-login count.
<<<
RELATIONS:
- TYPE: Parent
  VALUE: RQ-H10TG-93
  ROLE: Refines
- TYPE: Parent
  VALUE: RQ-H10TG-94
  ROLE: Refines
- TYPE: Parent
  VALUE: RQ-H10TG-282
  ROLE: Refines

[DESIGN_ITEM]
UID: SW-H10TG-250
TITLE: Prevent treatment plan execution if an interlock is active
STATEMENT: >>>
.. raw:: html

   <pre class="mermaid">
   sequenceDiagram
       autonumber

       box Application
           participant OperatePlanViewModelBase
           participant InterlockIndicators
           participant BeamOnCommand
           participant GCBDataStore
           participant SystemTelemetryProcessor
           participant TelemetryService
       end
       box ControlBoard
           participant Firmware
       end

       Firmware-->>TelemetryService: [UDP] unsolicited telemetry
       TelemetryService->>SystemTelemetryProcessor: Process datagram
       SystemTelemetryProcessor->>GCBDataStore: Set semantic snapshot
       GCBDataStore-->>OperatePlanViewModelBase: SystemTelemetryChanged

       activate OperatePlanViewModelBase
       Note over OperatePlanViewModelBase: Check semantic interlocks and active fault categories
       alt Interlock or fault is active
           OperatePlanViewModelBase->>BeamOnCommand: disable
       end
       deactivate OperatePlanViewModelBase

       GCBDataStore-->>InterlockIndicators: SystemTelemetryChanged
       InterlockIndicators->>InterlockIndicators: Render ready, active, or unavailable
   </pre>
<<<
RELATIONS:
- TYPE: Parent
  VALUE: RQ-H10TG-36
  ROLE: Refines

[DESIGN_ITEM]
UID: SW-H10TG-72
TITLE: Radiation Emission Control - Beam On process Sequence
STATEMENT: >>>
Before preparation, the treatment-plan validation requires one valid treatment field. A
missing, additional, or invalid field is rejected before any firmware-session command is
sent.

When the operator confirms completed delivery, External resets the timers, clears the
board plan, and awaits the EMR unload and local treatment clearing. Prepare remains
disabled while unloading and after an unload failure; a successful retry clears the
local plan and treatment before a new pending plan can be prepared.

The SQLite server publishes unloading only on the general PlanEvents stream. It does
not publish an unloaded plan as a LoadForTreatmentEvents request. External accepts
load-for-treatment notifications only for PendingLoad or PartialPendingLoad plans;
Loaded and Unloaded notifications cannot repopulate the treatment console.

Unloading and incoming plan events are serialized by the treatment task queue.
Completed-treatment recovery already runs in that queue and performs its awaited
unload inline, avoiding a wait on work queued behind itself.

.. raw:: html

   <pre class="mermaid">
   sequenceDiagram
       autonumber
       actor User
       participant ExtCC as Ext C and C
       participant Boards
       participant HVPS

       User->>ExtCC: Beam On
       activate ExtCC
       Note over ExtCC: Check if the state is Ready
       
       ExtCC->>Boards: Release Point
       activate Boards

       ExtCC->>HVPS: Filament set point
       activate HVPS
       Note over ExtCC: "Button shows Launching progress"
       Boards->>HVPS: Start scalar emission
       HVPS-->>ExtCC: Scalar emission finished
       deactivate HVPS
       Note over ExtCC: "Button shows Beaming on progress"
       deactivate Boards

       Note over ExtCC: "Button shows Clear Timers"
       deactivate ExtCC

       User->>ExtCC: Clear Timers
       activate ExtCC
       ExtCC->>Boards: Clear Timers
       activate Boards
       deactivate Boards
       deactivate ExtCC

       User->>ExtCC: Unload Plan
       activate ExtCC
       ExtCC->>Boards: Unload Plan
       activate Boards
       deactivate Boards
       deactivate ExtCC
   </pre>

.. raw:: html

   <pre class="mermaid">
   sequenceDiagram
       autonumber
       actor User

       box Application
           participant PlanViewModel
           participant PlanModel
       end

       box Server
           participant Storage
       end

       User->>PlanViewModel: refresh treatment fields
       activate PlanViewModel
       PlanViewModel->>PlanModel: fetch fields
       activate PlanModel
       
       Note over PlanModel: clear displayed fields
       PlanModel->>Storage: query stored fields
       activate Storage
       Note over Storage: handle request
       Storage-->>PlanModel: treatment fields
       deactivate Storage
       
       Note over PlanModel: update displayed fields
       PlanModel-->>PlanViewModel: 
       PlanViewModel-->>User: display fields

       PlanViewModel->>PlanModel: validate field doses
       Note over PlanModel: verify dose calculations
       PlanModel-->>PlanViewModel: validity status
       deactivate PlanModel

       alt "validation fails"
           Note over PlanViewModel: disable treatment
           PlanViewModel-->>User: show warning
       end
       deactivate PlanViewModel
   </pre>
<<<
RELATIONS:
- TYPE: Parent
  VALUE: RQ-H10TG-9
  ROLE: Refines
- TYPE: Parent
  VALUE: RQ-H10TG-247
  ROLE: Refines

[DESIGN_ITEM]
UID: SW-H10TG-74
TITLE: Radiation Emission Control - Resume Beam-On process after error is cleared - Sequence
STATEMENT: >>>
.. raw:: html

   <pre class="mermaid">
   sequenceDiagram
       autonumber
       actor User
       participant ExtCC as Ext C and C
       participant Boards
       participant HVPS

       HVPS->>Boards: Error
       activate HVPS
       activate Boards
       Boards->>ExtCC: Error
       deactivate Boards
       deactivate HVPS
       
       activate ExtCC
       Note over ExtCC: Show error indication to the user
       Note over ExtCC: "Button shows Clear Error"
       deactivate ExtCC

       User->>ExtCC: Clear Errors
       activate ExtCC
       ExtCC->>Boards: Clear Errors
       activate Boards
       deactivate Boards
       deactivate ExtCC

       User->>ExtCC: Reset timers
       activate ExtCC
       ExtCC->>Boards: Reset timers
       activate Boards
       deactivate Boards
       deactivate ExtCC

       Note over ExtCC: "Button shows Continue"
       User->>ExtCC: Continue
       activate ExtCC
       Note over ExtCC: Check if status is STAGED
       
       rect rgb(235, 247, 235)
           Note left of ExtCC: Reconfirm plan before resume emission
           ExtCC->>Boards: "Re-send scalar emission info with remaining duration (confirmation)"
           activate Boards
           deactivate Boards
           ExtCC->>Boards: Release Plan Command
           activate Boards
           Boards->>HVPS: Ramp HV
           activate HVPS
           HVPS-->>Boards: "HV ramp feedback. Setpoint reached"
           deactivate HVPS
           Boards-->>ExtCC: In ready State
           deactivate Boards
       end

       rect rgb(253, 238, 238)
           Note left of ExtCC: Resume emission
           ExtCC->>Boards: Release point command
           activate Boards
           Boards->>Boards: Run the same scalar emission
           deactivate Boards
       end
       deactivate ExtCC
   </pre>
<<<
RELATIONS:
- TYPE: Parent
  VALUE: RQ-H10TG-73
  ROLE: Refines

[DESIGN_ITEM]
UID: SW-H10TG-76
TITLE: Radiation Emission Control - Resume Prepare process after error is cleared - Sequence
STATEMENT: >>>
.. raw:: html

   <pre class="mermaid">
   sequenceDiagram
       autonumber
       actor User

       box Application
           participant PlanViewModel
           participant PlanModel
       end

       box Server
           participant Storage
       end

       User->>PlanViewModel: refresh treatment fields
       activate PlanViewModel
       PlanViewModel->>PlanModel: fetch fields
       activate PlanModel
       
       Note over PlanModel: clear displayed fields
       PlanModel->>Storage: query stored fields
       activate Storage
       Note over Storage: handle request
       Storage-->>PlanModel: treatment fields
       deactivate Storage
       
       Note over PlanModel: update displayed fields
       PlanModel-->>PlanViewModel: 
       PlanViewModel-->>User: display fields

       PlanViewModel->>PlanModel: validate field doses
       Note over PlanModel: verify dose calculations
       PlanModel-->>PlanViewModel: validity status
       deactivate PlanModel

       alt "validation fails"
           Note over PlanViewModel: disable treatment
           PlanViewModel-->>User: show warning
       end
       deactivate PlanViewModel
   </pre>
<<<
RELATIONS:
- TYPE: Parent
  VALUE: RQ-H10TG-75
  ROLE: Refines

[DESIGN_ITEM]
UID: SW-H10TG-33
TITLE: Radiation Emission View - Treatment Plan Staging Operational Point Parameters
STATEMENT: >>>
The application shall initiate a new firmware session with an argument-free staging
request, then send the parameters for exactly one scalar emission.

The scalar emission includes acceleration potential, emission current, delivery time,
remaining time, focus and deflection adjustments, and filament current. Each value must be
within its configured operating range.
<<<
RELATIONS:
- TYPE: Parent
  VALUE: RQ-H10TG-31
  ROLE: Refines

[DESIGN_ITEM]
UID: SW-H10TG-257
TITLE: Record Delivered Dose
STATEMENT: >>>

.. raw:: html

   <pre class="mermaid">
   sequenceDiagram
       autonumber
       
       box Application
           participant OperatePlanViewModelBase
           participant TreatmentModel
           participant ActualTreatmentFieldModel
           participant MainBoardModel
           participant TelemetryService
       end
       box ControlBoard
           participant Firmware
       end
       box Database
           participant TreatmentService
           participant ActualTreatmentFieldService
       end

       Note over OperatePlanViewModelBase, ActualTreatmentFieldService: User initiates emission delivery
       
       OperatePlanViewModelBase->>TreatmentModel: create new treatment
       activate OperatePlanViewModelBase
       activate TreatmentModel
       TreatmentModel->>TreatmentService: "grpc: CreateTreatment"
       activate TreatmentService
       Note over TreatmentService: create DB record
       TreatmentService-->>TreatmentModel: stored record
       deactivate TreatmentService
       deactivate TreatmentModel

       loop "[Unsolicited semantic telemetry]"
           Firmware-->>TelemetryService: "[UDP] telemetry packet"
           activate TelemetryService
           TelemetryService-->>OperatePlanViewModelBase: immutable telemetry snapshot
           deactivate TelemetryService
           
           alt "[Emission state: update the application-selected field from telemetry]"
               Note over OperatePlanViewModelBase: use application-owned ActiveEmissionIndex
               OperatePlanViewModelBase->>OperatePlanViewModelBase:
               Note over OperatePlanViewModelBase: get scalar telemetry timer values
               OperatePlanViewModelBase->>OperatePlanViewModelBase:
               OperatePlanViewModelBase->>ActualTreatmentFieldModel: "SaveActualTreatmentField(treatment, ActiveEmissionIndex, timer)"
           end
       end

       alt "[Leaving Emission state: update the application-selected field from the board]"
           OperatePlanViewModelBase->>MainBoardModel: query scalar emission data
           activate MainBoardModel
           MainBoardModel->>Firmware: indexless query emission data
           activate Firmware
           Firmware-->>MainBoardModel: scalar data response
           deactivate Firmware
           MainBoardModel-->>OperatePlanViewModelBase: scalar emission data
           deactivate MainBoardModel

           Note over OperatePlanViewModelBase: get timer value from scalar data
           OperatePlanViewModelBase->>OperatePlanViewModelBase:
           OperatePlanViewModelBase->>ActualTreatmentFieldModel: "SaveActualTreatmentField(treatment, ActiveEmissionIndex, timer)"
           activate ActualTreatmentFieldModel
           
           alt "[new actual treatment field data]"
               ActualTreatmentFieldModel->>ActualTreatmentFieldService: "grpc: CreateActualTreatmentField"
               activate ActualTreatmentFieldService
               Note over ActualTreatmentFieldService: create DB record
               ActualTreatmentFieldService-->>ActualTreatmentFieldModel: stored record
               deactivate ActualTreatmentFieldService
           end
           
           alt "[existing actual treatment field data]"
               ActualTreatmentFieldModel->>ActualTreatmentFieldService: "grpc: UpdateActualTreatmentField"
               activate ActualTreatmentFieldService
               Note over ActualTreatmentFieldService: update DB record
               ActualTreatmentFieldService-->>ActualTreatmentFieldModel: stored record
               deactivate ActualTreatmentFieldService
           end
           deactivate ActualTreatmentFieldModel
       end
       deactivate OperatePlanViewModelBase
   </pre>
<<<
RELATIONS:
- TYPE: Parent
  VALUE: RQ-H10TG-21
  ROLE: Refines
- TYPE: Parent
  VALUE: RQ-H10TG-22
  ROLE: Refines

[DESIGN_ITEM]
UID: SW-H10TG-252
TITLE: Restrict window switching during active emission
STATEMENT: >>>


.. raw:: html

   <pre class="mermaid">
   sequenceDiagram
       autonumber
       actor User
       
       box Application
           participant OperatePlanViewModelBase
           participant MainBoardModel
           participant UIStateMachine
           participant TabControl
       end

       User->>OperatePlanViewModelBase: Prepare
       activate OperatePlanViewModelBase
       
       OperatePlanViewModelBase->>MainBoardModel: LoadPlan
       activate MainBoardModel
       Note over MainBoardModel: create session and load plan to the Board
       MainBoardModel->>MainBoardModel: 
       Note over MainBoardModel: wait for Ready state
       MainBoardModel->>MainBoardModel: 
       
       MainBoardModel-->>OperatePlanViewModelBase: LoadPlan task result
       deactivate MainBoardModel

       OperatePlanViewModelBase->>UIStateMachine: lock on current tab
       activate UIStateMachine
       UIStateMachine->>TabControl: notify on lock flag change
       activate TabControl
       Note over TabControl: "disable tab switch"
       TabControl->>TabControl: 
       TabControl-->>UIStateMachine: 
       deactivate TabControl
       UIStateMachine-->>OperatePlanViewModelBase: 
       deactivate UIStateMachine

       Note over OperatePlanViewModelBase: enable BeamOn command
       OperatePlanViewModelBase->>OperatePlanViewModelBase: 
       Note over OperatePlanViewModelBase: enable ClearPlan command
       OperatePlanViewModelBase->>OperatePlanViewModelBase: 
       
       OperatePlanViewModelBase->>User: "ClearPlan/BeamOn?"
       deactivate OperatePlanViewModelBase
   </pre>
<<<
RELATIONS:
- TYPE: Parent
  VALUE: RQ-H10TG-49
  ROLE: Refines

[DESIGN_ITEM]
UID: SW-H10TG-270
TITLE: Retrieve Fault Information from Firmware
STATEMENT: >>>
The command interface retrieves a coherent snapshot of the latched fault list using indexed
requests. Each 45-word response is validated for packet shape, index, count, clear epoch,
fault category, printable NUL-terminated format string, format checksum, and argument count.
The interface retries the snapshot up to three times if the clear epoch changes during
retrieval. The main-board model replaces the GCB data store's active list only after a
coherent snapshot has been assembled.

.. raw:: html

    <pre class="mermaid">
    sequenceDiagram
        participant FaultsViewModel
        participant MainBoardModel
        participant GcbCommandInterface
        participant FaultEntryParser
        participant Firmware
        participant GCBDataStore

        FaultsViewModel->>MainBoardModel: GetFaults
        MainBoardModel->>GcbCommandInterface: GetFaults
        loop Entry index 0 through active count - 1
            GcbCommandInterface->>Firmware: [UDP] FaultInfoRequest(index)
            Firmware-->>GcbCommandInterface: [UDP] FaultInfoResponse(45 words)
            GcbCommandInterface->>FaultEntryParser: Validate and format entry
        end
        GcbCommandInterface-->>MainBoardModel: FaultSnapshot(epoch, entries)
        MainBoardModel->>GCBDataStore: ReplaceFaults
        GCBDataStore-->>FaultsViewModel: FaultsChangedEvent
    </pre>
<<<
RELATIONS:
- TYPE: Parent
  VALUE: RQ-H10TG-284
  ROLE: Refines

[DESIGN_ITEM]
UID: SW-H10TG-261
TITLE: Retrieve Quality Checks Reports
STATEMENT: >>>
The flow for retrieving Quality Checks Report should be implemented as described in the following sequence diagram:

.. raw:: html

    <pre class="mermaid">
    sequenceDiagram
        autonumber
        actor User
        box Application
            participant VM as QualityCheckReportsViewModel
            participant M as QcModel
        end
        box Database
            participant S as QC Services
        end

        VM->>VM: build list of QC configurations
        
        User->>VM: select collimator type and energy
        VM->>VM: find matching collimator configuration
        
        VM->>M: read configuration QC samples
        M->>S: grpc: read QC samples
        S-->>M: grpc: stored samples
        M-->>VM: list of samples
        VM-->>User: [Show list of samples]

        User->>VM: select a sample
        VM->>M: fetch sample data
        M->>S: read sample fields/intensities
        S-->>M: grpc: stored records
        M-->>VM: sample data

        VM->>M: fetch reference sample data
        M->>M: check for cached data
        
        alt No cached sample data
            M->>S: read sample fields/intensities
            S-->>M: grpc: stored records
            M->>M: cache as reference
        end
        
        M-->>VM: reference sample data
        
        VM->>VM: calc sample deviation from reference
        VM->>VM: update sample report view
        VM-->>User: [Display updated report]

        User->>VM: switch raw/deviation report mode
    </pre>
<<<
RELATIONS:
- TYPE: Parent
  VALUE: RQ-H10TG-93
  ROLE: Refines
- TYPE: Parent
  VALUE: RQ-H10TG-94
  ROLE: Refines

[DESIGN_ITEM]
UID: SW-H10TG-274
TITLE: Retrieve treated patient details
STATEMENT: >>>
When the application is loaded, it searches for a plan that is pending to be loaded. Then, the plan details and all the patients' clinical data are initialized.

.. raw:: html

    <pre class="mermaid">
    sequenceDiagram
        participant Object as :Object
        participant OutdoorViewModel
        participant PlanModel
        participant TreatmentFieldCommands
        participant PrescriptionCommands
        participant TreatmentCommands

        [?] ->> Object: dispatch
        activate Object
        Object->>OutdoorViewModel: LookForPlanAsync
        activate OutdoorViewModel
        
        OutdoorViewModel->>PlanModel: LookPendingPlan
        activate PlanModel
        OutdoorViewModel->>Object: callback
        activate Object
        Object-->>OutdoorViewModel: return
        deactivate Object
        
        OutdoorViewModel->>PlanModel: SetPlan
        OutdoorViewModel-->>Object: return
        deactivate OutdoorViewModel
        
        PlanModel->>TreatmentFieldCommands: ReadFieldsAsync
        activate TreatmentFieldCommands
        deactivate TreatmentFieldCommands
        
        PlanModel->>PrescriptionCommands: ReadAsync
        activate PrescriptionCommands
        deactivate PrescriptionCommands
        
        PlanModel->>TreatmentCommands: Text
        activate TreatmentCommands
        deactivate TreatmentCommands
        
        deactivate PlanModel
        deactivate Object
    </pre>
<<<
RELATIONS:
- TYPE: Parent
  VALUE: RQ-H10TG-85
  ROLE: Refines

[DESIGN_ITEM]
UID: SW-H10TG-273
TITLE: Show message for DB communication error
STATEMENT: >>>
The application will show a DB Communication error when the gRPC command throws a timeout exception. The exception will be populated through the MVVM model.

.. raw:: html

    <pre class="mermaid">
    sequenceDiagram
        box Application
            participant View
            participant ViewModel
            participant Model
            participant gRPCCommand
        end
        box Database
            participant Object as :Object
        end

        activate View
        View->>ViewModel: call
        activate ViewModel
        ViewModel->>Model: call
        activate Model
        Model->>gRPCCommand: call
        activate gRPCCommand
        gRPCCommand->>Object: call
        activate Object
        
        Object-->>gRPCCommand: GRPC_STATUS_DEADLINE_EXCEEDED
        deactivate Object
        
        gRPCCommand-->>Model: throw ex
        deactivate gRPCCommand
        Model-->>ViewModel: throw ex
        deactivate Model
        ViewModel-->>View: throw ex
        deactivate ViewModel
        
        View->>View: Show DB Communication Error message
        deactivate View
    </pre>
<<<
RELATIONS:
- TYPE: Parent
  VALUE: RQ-H10TG-288
  ROLE: Refines

[DESIGN_ITEM]
UID: SW-H10TG-263
TITLE: Stop Emission
STATEMENT: >>>
The flow for stopping an emission should be implemented as described in the following sequence diagram:

.. image:: _assets/SW-H10TG-263.png
<<<
RELATIONS:
- TYPE: Parent
  VALUE: RQ-H10TG-3
  ROLE: Refines

[DESIGN_ITEM]
UID: SW-H10TG-20
TITLE: Treatment Console - Activate emission delivery - Buttons' State
STATEMENT: >>>
The following are the labels and the enabled/disabled state of the buttons in every system state:

+--------------------------------------------------------------+-------------------------------+------------------------------+----------------------------------------------------------------+
| User Action                                                  | Machine State                 | Buttons' Label               | Buttons State                                                  |
+==============================================================+===============================+==============================+================================================================+
| Start                                                        | COLD                          | Prepare Beam-On Stop         | Prepare - Enabled Beam-On - Disabled Stop - Disabled           |
+--------------------------------------------------------------+-------------------------------+------------------------------+----------------------------------------------------------------+
| Prepare is pressed                                           | WARMUP                        | Warming Up Beam-On Stop      | Warming Up - progress bar Beam-On - Disabled Stop - Enabled    |
+--------------------------------------------------------------+-------------------------------+------------------------------+----------------------------------------------------------------+
|                                                              | PRIMED ->Staged               | Loading Beam-On Stop         | Loading - progress bar Beam-On - Disabled Stop - Enabled       |
+--------------------------------------------------------------+-------------------------------+------------------------------+----------------------------------------------------------------+
|                                                              | READY                         | Clear Plan Beam-On Stop      | Clear Plan - Enabled Beam-On - Enabled Stop - Disabled         |
+--------------------------------------------------------------+-------------------------------+------------------------------+----------------------------------------------------------------+
| Beam-On is pressed                                           | LAUNCHING                     | Clear Plan                   | Clear Plan - Disabled                                          |
+--------------------------------------------------------------+-------------------------------+------------------------------+----------------------------------------------------------------+
|                                                              |                               | Launching Stop               | Launching - progress bar Stop - Enabled                        |
+--------------------------------------------------------------+-------------------------------+------------------------------+----------------------------------------------------------------+
|                                                              | EMISSION                      | Clear Plan Beaming-On Stop   | Clear Plan - Disabled Beaming-On - progress bar Stop - Enabled |
+--------------------------------------------------------------+-------------------------------+------------------------------+----------------------------------------------------------------+
|                                                              | STAGED                        | Clear Plan Reset Timers Stop | Clear Plan - Disabled Reset Timers - Enabled Stop - Disabled   |
+--------------------------------------------------------------+-------------------------------+------------------------------+----------------------------------------------------------------+
| Reset Timers is pressed                                      | STAGED/COLD                   | Clear Plan Beam-On Stop      | Clear Plan - Enabled Beam-On - Disabled Stop - Disabled        |
+--------------------------------------------------------------+-------------------------------+------------------------------+----------------------------------------------------------------+
| Fault occurred during Prepare                                | FAULT/COLD FAULT              | Clear Error Beam-On Stop     | Clear Error - Enabled Beam-On - Disabled Stop - Disabled       |
+--------------------------------------------------------------+-------------------------------+------------------------------+----------------------------------------------------------------+
| Clear Errors during Prepare is pressed                       | Fault->Warmup-> PRIMED        | Prepare Beam-On Stop         | Prepare - Enabled Beam On - Disabled Stop - Disabled           |
+--------------------------------------------------------------+-------------------------------+------------------------------+----------------------------------------------------------------+
| Fault occurred during Emission                               | FAULT/COLD FAULT              | Clear Plan Clear Error Stop  | Clear Plan - Disabled Clear Error - Enabled Stop - Disabled    |
+--------------------------------------------------------------+-------------------------------+------------------------------+----------------------------------------------------------------+
|                                                              |                               |                              |                                                                |
+--------------------------------------------------------------+-------------------------------+------------------------------+----------------------------------------------------------------+
| Clear Errors during emission is pressed ( also Clear timers) | Fault->Warmup-> PRIMED/STAGED | Clear Plan Resume Stop       | Clear Plan - enabled Resume - Enabled Stop- Disabled           |
+--------------------------------------------------------------+-------------------------------+------------------------------+----------------------------------------------------------------+
| Resume is Pressed                                            | READY                         | Clear Plan Beam-ON Stop      | Clear Plan - Enabled Beam-On- Enabled Stop - Disabled          |
+--------------------------------------------------------------+-------------------------------+------------------------------+----------------------------------------------------------------+
<<<
RELATIONS:
- TYPE: Parent
  VALUE: RQ-H10TG-53
  ROLE: Refines

[DESIGN_ITEM]
UID: SW-H10TG-19
TITLE: Treatment Console - Load plan into GB board Flow
STATEMENT: >>>
The plan loading flow:

.. image:: _assets/SW-H10TG-19.png
<<<
RELATIONS:
- TYPE: Parent
  VALUE: RQ-H10TG-43
  ROLE: Refines
- TYPE: Parent
  VALUE: RQ-H10TG-90
  ROLE: Refines

[DESIGN_ITEM]
UID: SW-H10TG-18
TITLE: Treatment Console - Radiation Emission View - State Machine
STATEMENT: >>>
The radiation emission should be implemented according to the emission board state machine.

.. image:: _assets/SW-H10TG-18.png
<<<
RELATIONS:
- TYPE: Parent
  VALUE: RQ-H10TG-105
  ROLE: Refines
- TYPE: Parent
  VALUE: RQ-H10TG-160
  ROLE: Refines
- TYPE: Parent
  VALUE: RQ-H10TG-161
  ROLE: Refines

[DESIGN_ITEM]
UID: SW-H10TG-254
TITLE: Treatment Fields Emission Progress indicators
STATEMENT: >>>
Emission progress consumes immutable semantic snapshots published from unsolicited
telemetry. The application-owned ActiveEmissionIndex identifies the current business field;
the firmware telemetry contains no point index or point count. During emission, scalar
timer values determine emission progress; during launching, the heater-current setpoint
determines launching progress.

.. raw:: html

    <pre class="mermaid">
    sequenceDiagram
        participant VM as OperatePlanViewModelBase
        participant CC as CollimatorControl
        participant TFL as TreatmentFieldList
        participant EP as EmissionProgress
        participant DS as GCBDataStore

        DS-->>VM: SystemTelemetryChanged(immutable snapshot)
        VM->>VM: Read application-owned ActiveEmissionIndex
        VM->>CC: Keep prepared field selection
        VM->>TFL: Keep prepared field selection
        alt Emission state
            VM->>VM: Calculate emission progress from timers
            VM->>EP: Set emission progress
        else Launching state
            VM->>VM: Calculate launching progress from heater setpoint
            VM->>EP: Set launching progress
        end
    </pre>
<<<
RELATIONS:
- TYPE: Parent
  VALUE: RQ-H10TG-4
  ROLE: Refines
- TYPE: Parent
  VALUE: RQ-H10TG-10
  ROLE: Refines
- TYPE: Parent
  VALUE: RQ-H10TG-95
  ROLE: Refines

[DESIGN_ITEM]
UID: SW-H10TG-248
TITLE: Treatment Staging Sequence
STATEMENT: >>>

.. raw:: html

    <pre class="mermaid">
    sequenceDiagram
        box Application
            participant M as MainBoardModel
        end
        box ControlBoard
            participant F as Firmware
        end

        Note over M, F: Board is in Primed state, User initiates plan preparation

        M->>F: [UDP] create an argument-free scalar session
        activate F
        F-->>M: [UDP] session key
        deactivate F

        M->>M: wait for Staging board state

        M->>F: [UDP] send scalar emission parameters
        activate F
        F-->>M: [UDP] status response
        deactivate F

        M->>F: [UDP] Stage command
        activate F
        F-->>M: [UDP] status response
        deactivate F

        M->>M: wait for Staged board state
    </pre>
<<<
RELATIONS:
- TYPE: Parent
  VALUE: RQ-H10TG-31
  ROLE: Refines
- TYPE: Parent
  VALUE: RQ-H10TG-34
  ROLE: Refines

[DESIGN_ITEM]
UID: SW-H10TG-268
TITLE: Treatment View Layout
STATEMENT: >>>
The layout should include:

1. The plan's treatment fields are listed on a table.
2. A visual representation of the collimator.
3. The system telemetry: System status, Main timer (in sec), backup timers (T1 & T2) (in sec), Energy (in kV), and Current ( in mA).
4. Prepare button - which will prepare the system for the radiation (i.e., warmup and loading).
5. Beam-On - a multi-state control for triggering the emission, resetting timers, and clearing errors.
6. Stop button - Stops the emission.
7. Interlocks visualization.
8. Live Camera to monitor the patient.

.. image:: _assets/SW-H10TG-268.png
<<<
RELATIONS:
- TYPE: Parent
  VALUE: RQ-H10TG-13
  ROLE: Refines
- TYPE: Parent
  VALUE: RQ-H10TG-281
  ROLE: Refines

[DESIGN_ITEM]
UID: SW-H10TG-276
TITLE: Validate Active Collimator
STATEMENT: >>>
The flow for validating the active collimator when performing Quality Checks should be implemented as described in the following sequence diagram:

<<<
RELATIONS:
- TYPE: Parent
  VALUE: RQ-H10TG-279
  ROLE: Refines

[DESIGN_ITEM]
UID: SW-H10TG-256
TITLE: Warmup Progress Monitoring
STATEMENT: >>>
Warmup progress consumes immutable semantic snapshots published from unsolicited telemetry.
The warmup model uses the available heater-current setpoint to calculate and publish the
progress value.

.. raw:: html

    <pre class="mermaid">
    sequenceDiagram
        participant M as WarmupModel
        participant WP as WarmupProgress
        participant DS as GCBDataStore

        Note over M, DS: User initiates Warmup/Conditioning
        DS-->>M: SystemTelemetryChanged(immutable snapshot)
        M->>M: Read available HeaterCurrentSetpoint
        M->>M: Calculate warmup progress
        M->>WP: Notify progress value change
    </pre>
<<<
RELATIONS:
- TYPE: Parent
  VALUE: RQ-H10TG-12
  ROLE: Refines

[DESIGN_ITEM]
UID: SW-H10TG-251
TITLE: prompt the user when an interlock triggered during emission
STATEMENT: >>>
.. raw:: html

    <pre class="mermaid">
    sequenceDiagram
        actor User
        participant VM as OperatePlanViewModelBase
        participant M as MainBoardModel
        participant D as DialogService
        participant DS as GCBDataStore
        participant F as Firmware

        User->>VM: BeamOn
        VM->>M: BeamOn
        M->>F: [UDP] ReleasePoint command
        F-->>M: [UDP] command response
        M->>M: Wait for emission termination

        F-->>DS: Unsolicited telemetry routed through processor
        DS-->>VM: SystemTelemetryChanged
        VM->>VM: Check control-board state and active faults

        alt Board is in Fault state
            VM->>M: Cancel current task
            M-->>VM: BeamOn task cancellation exception
            VM->>D: Show emission error dialog
            D-->>User: Error dialog
        end
    </pre>
<<<
RELATIONS:
- TYPE: Parent
  VALUE: RQ-H10TG-73
  ROLE: Refines

[DESIGN_ITEM]
UID: SW-H10TG-279
TITLE: Calibration Mode Clinical Lockout
STATEMENT: >>>
The external tab view binds each clinical tab's enabled state to the immutable telemetry
firmware mode in addition to the existing plan-loaded navigation constraint. Calibration
mode disables the Treatment and Quality Assurance tabs. A high-z-order overlay inside each
tab obscures previously rendered content and displays the service-required message.
Unknown or unavailable firmware mode does not lock the tabs.
<<<
RELATIONS:
- TYPE: Parent
  VALUE: RQ-H10TG-285
  ROLE: Refines

[DESIGN_ITEM]
UID: SW-H10TG-280
TITLE: Display Main Control Firmware Version
STATEMENT: >>>
The version-information parser accepts the 19-word control-board response and decodes its
null-padded 32-byte ASCII version fields. When the user opens System Information, the
external tab view requests device information and displays the decoded main-control
``FirmwareVersion`` string.
<<<
RELATIONS:
- TYPE: Parent
  VALUE: RQ-H10TG-286
  ROLE: Refines

[DESIGN_ITEM]
UID: SW-H10TG-283
TITLE: Permission-Based Navigation Composition
STATEMENT: >>>
The external application derives the visible navigation items from the authenticated user's
permissions when composing the left navigation menu and Quality Assurance tabs. The
Treatment menu item requires treatment permission, and the Physics tab requires physics
quality-assurance permission. Items for which the user lacks permission are omitted rather
than displayed as actionable controls.
<<<
RELATIONS:
- TYPE: Parent
  VALUE: RQ-H10TG-287
  ROLE: Refines

[[/SECTION]]

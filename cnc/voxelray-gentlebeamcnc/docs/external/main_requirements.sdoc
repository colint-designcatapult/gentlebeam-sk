[DOCUMENT]
TITLE: GBSK Software Requirements Specification for External GUI
UID: DHF-GBSK-0007
METADATA:
  COMPONENT: heracles-external-gui

[GRAMMAR]
IMPORT_FROM_FILE: @grammar

[[SECTION]]
TITLE: Purpose

[TEXT]
STATEMENT: >>>
The purpose of this document is to provide Software Requirements Specifications for the GBSK External GUI Software.
<<<

[[/SECTION]]

[[SECTION]]
TITLE: Scope

[TEXT]
STATEMENT: >>>
This document describes all requirements of the GBSK External GUI Software.

The information in this document is derived from the VoxelRay GBSK Product Requirements Specification, referenced in this document.

*The term Software applies to both Software and Firmware systems.*
<<<

[[/SECTION]]

[[SECTION]]
TITLE: Abbreviations and Definitions

[TEXT]
STATEMENT: >>>
GUI
  Graphic User Interface

PRS
  Product Requirements Specification

SDP
  Software Development Plan

SRS
  Software Requirements Specification

SW
  Software
<<<

[[/SECTION]]

[[SECTION]]
TITLE: Overview

[TEXT]
STATEMENT: >>>
The external GUI console provides a means for the user to activate and monitor the treatment. It communicates with the main control board and treatment head camera.

The external GUI software runs on the external tablet console located outside the room.
<<<

[[/SECTION]]

[[SECTION]]
TITLE: References

[TEXT]
STATEMENT: >>>
Document ID / Reference Number: DHF-GBSK-0001
Document TITLE: GBSK Software Development Plan (SDP)

Document ID / Reference Number: DHF-GBSK-0002
Document Title: VoxelRay Product Requirements Specification (PRS)
<<<

[[/SECTION]]

[[SECTION]]
PREFIX: RQ-H10TG-
TITLE: Requirements

[REQUIREMENT]
UID: RQ-H10TG-1
TYPE: Functional
TITLE: Quality Assurance - Daily Warmup
STATEMENT: >>>
The application shall provide a control that allows an operator to initiate a daily warm-up, which will prepare the system for radiation emission.

.. image:: _assets/RQ-H10TG-1.png
<<<

[REQUIREMENT]
UID: RQ-H10TG-4
TYPE: Functional
TITLE: Treatment View - Treatment Parameters Emission Progress indicator
STATEMENT: >>>
The application shall provide a UI indicator that allows users to monitor the progress of emission treatment parameters.

.. image:: _assets/RQ-H10TG-4.png
<<<

[REQUIREMENT]
UID: RQ-H10TG-8
TYPE: Functional
TITLE: Treatment View - Plan details view
STATEMENT: >>>
The application shall provide an interface allowing the operator to view the treatment plan details with the following parameters:

* Treatment fields table - A table view representing the fields as defined in the treatment plan, and includes the following columns:

  * Energy level [kVp].
  * Duration [sec].
  * Current [mA].
  * Actual duration [sec] - A column representing the actual time the emission was delivered.
  * Remaining duration [sec]
<<<

[REQUIREMENT]
UID: RQ-H10TG-9
TYPE: Functional
TITLE: Treatment View - Beam On process
STATEMENT: >>>
The treatment console shall provide a control that allows the user to initiate/trigger radiation emission.
A clinical treatment shall contain exactly one treatment field. One preparation creates one
firmware session containing one scalar emission, and one Beam On action releases that
emission.

The interface should include a multi-state control that includes the following states:

* Launch - Triggers the launching phase before beaming on.
* Beam-On - Initiate the radiation emission as the treatment plan requires.
* Reset - Resets the emission parameters, i.e., the timers.

The label of the control should be changed according to its state.

The states will vary from Prepare->Warmup->Load and Launch->Beam On->Reset.

The state of the labels will be changed according to the state machine.
<<<

[REQUIREMENT]
UID: RQ-H10TG-10
TYPE: Functional
TITLE: Treatment View - Emission Progress Indicators
STATEMENT: >>>
The application shall provide an interface allowing the operator to monitor the progress of the delivered emission of a treatment plan.

.. image:: _assets/RQ-H10TG-10.png
<<<

[REQUIREMENT]
UID: RQ-H10TG-12
TYPE: Functional
TITLE: Treatment View - Warmup Progress Monitoring
STATEMENT: >>>
The application shall provide an interface that allows the user to monitor the progress of the warm-up prior to the high-voltage ramp-up as part of the Prepare process for a treatment.
<<<

[REQUIREMENT]
UID: RQ-H10TG-21
TYPE: Functional
TITLE: Treatment View - Record Delivered Dose
STATEMENT: >>>
The application should record (save to the database) the time and dose of any radiation delivered in the 'treatment history' for the treated patient.
<<<

[REQUIREMENT]
UID: RQ-H10TG-22
TYPE: Functional
TITLE: Treatment View - Record partial treatment
STATEMENT: >>>
The application shall record any partial treatments in a resolution of 0.01 minutes (600 msec) and mark this treatment field as partial in the DB.
<<<

[REQUIREMENT]
UID: RQ-H10TG-26
TYPE: Functional
TITLE: Treatment View - Initialize the System
STATEMENT: >>>
The application shall implement functionality to initialize the firmware, instructing it to transition out of the startup state and into the cold state.
<<<

[REQUIREMENT]
UID: RQ-H10TG-29
TYPE: Functional
TITLE: Treatment View - Filament Conditioning
STATEMENT: >>>
The application shall implement functionality to request filament conditioning from the firmware by specifying the target filament current. The application shall ensure that the target current is within valid operational limits before sending the request to the firmware.
<<<

[REQUIREMENT]
UID: RQ-H10TG-30
TYPE: Functional
TITLE: Treatment View - Perform System Warmup in COLD State
STATEMENT: >>>
The application shall request system warmup only from the COLD state and shall inform the
operator when a safety prerequisite prevents the firmware from starting the procedure.
<<<

[REQUIREMENT]
UID: RQ-H10TG-31
TYPE: Functional
TITLE: Treatment View - Treatment Plan Staging
STATEMENT: >>>
The application shall initiate treatment staging with an argument-free new-session request
while the firmware is in the "PRIMED" state. The response shall contain a session ID. The
application shall then load exactly one scalar operational point for that session.
<<<

[REQUIREMENT]
UID: RQ-H10TG-32
TYPE: Functional
TITLE: Treatment View - Load a Treatment Plan
STATEMENT: >>>
The application shall load exactly one scalar operational point into each firmware session.
<<<

[REQUIREMENT]
UID: RQ-H10TG-34
TYPE: Functional
TITLE: Treatment View - Treatment Plan Confirmation
STATEMENT: >>>
The application shall receive one confirmation response for the singular operational point
in the firmware session.
<<<

[REQUIREMENT]
UID: RQ-H10TG-35
TYPE: Functional
TITLE: Treatment View - Confirmation of Treatment Plan
STATEMENT: >>>
The application shall confirm the operational point parameters of the treatment plan only after the staging process has been successfully completed.
<<<

[REQUIREMENT]
UID: RQ-H10TG-43
TYPE: Functional
TITLE: Treatment View - Radiation Emission Control - Prepare process
STATEMENT: >>>
The application shall provide an interface allowing the user to prepare the system for radiation emission. The preparation will include system warm-up and high voltage ramp-up.
<<<

[REQUIREMENT]
UID: RQ-H10TG-52
TYPE: Functional
TITLE: Treatment View - Enable window switching after emission delivery.
STATEMENT: >>>
The application shall enable the left tab bar when the emission is completed, and the plan is unloaded.
<<<

[REQUIREMENT]
UID: RQ-H10TG-53
TYPE: Functional
TITLE: Quality Assurance - Daily Warmup - Progress Monitoring
STATEMENT: >>>
The application shall provide an interface that allows the user to monitor the progress of the warm-up process.

.. image:: _assets/RQ-H10TG-53.png
<<<

[REQUIREMENT]
UID: RQ-H10TG-57
TYPE: Functional
TITLE: Treatment View - Daily Warmup - Log Performed Warmup
STATEMENT: >>>
The application shall log all (Full and Fast) warmups performed during the system's lifetime.
<<<

[REQUIREMENT]
UID: RQ-H10TG-73
TYPE: Functional
TITLE: Treatment View - Resume Beam On Process After Error Is Cleared
STATEMENT: >>>
The application shall have an interface allowing the user to resume an emission after a fault or interlock is cleared.

When the resume process is triggered, the emission should continue for the remaining duration.
<<<

[REQUIREMENT]
UID: RQ-H10TG-75
TYPE: Functional
TITLE: Treatment View - Resume Prepare process after the error is cleared
STATEMENT: >>>
The application shall have a control allowing the user to resume emission preparation after preparation interruption during warmup or high-voltage ramp-up.

The operator will retrigger the Prepare process after clearing the fault or interlock.
<<<

[REQUIREMENT]
UID: RQ-H10TG-89
TYPE: Functional
TITLE: Treatment View - Audit user's actions
STATEMENT: >>>
The application shall audit in the system log when the user triggers an action such as:

1. Triggering treatment preparation.
2. Triggering emission delivery.
3. Triggering stop emission

The audit shall identify the acting user and treatment context and distinguish an emission request from its measured delivery outcome, including completion, cancellation, or failure. Background telemetry and RPC activity alone shall not create user-action records.
<<<

[REQUIREMENT]
UID: RQ-H10TG-90
TYPE: Functional
TITLE: Treatment View - Enable Loading a Treatment Plan
STATEMENT: >>>
The application shall enable treatment plan loading only during staging periods.
<<<

[REQUIREMENT]
UID: RQ-H10TG-95
TYPE: Functional
TITLE: Treatment View - Emission Progress Indicators
STATEMENT: >>>
The application shall provide an interface allowing the operator to monitor the progress of an emission delivery.
<<<

[REQUIREMENT]
UID: RQ-H10TG-105
TYPE: Functional
TITLE: Treatment View - Reset Timers and Unload Plan after Treatment is Completed
STATEMENT: >>>
The application shall clear timers and unload a plan from the board and the UI when the treatment is finished.

The application will prompt the user with a pop-up message when the treatment is finished, and the emission is delivered successfully.

The info message will include an OK control, triggering a timer reset and unloading the plan.
<<<

[REQUIREMENT]
UID: RQ-H10TG-160
TYPE: Functional
TITLE: Load For Treatment - Resume Uncompleted Treatment Alert
STATEMENT: >>>
The application shall alert the operator if the loaded plan was not completely delivered and enable the operator to choose to deliver the remaining plan (i.e., resume the treatment) or deliver the whole treatment plan.
<<<

[REQUIREMENT]
UID: RQ-H10TG-161
TYPE: Functional
TITLE: Load For Treatment - Resume Uncompleted Treatment
STATEMENT: >>>
The application shall enable the operator to resume uncompleted treatment. In case the last treatment was stopped in the middle and the delivery of the treatment plan was not completed, the operator should be able to resume the delivery of the remaining treatment.

When a plan is loaded, the application should query the latest treatment and check if this treatment is marked as completed. If not, it will pop up a message to the user about the uncompleted treatment.

If the user chooses to resume the treatment, the application should calculate the remaining time and use this as the plan to be delivered.

If the user chooses not to resume, the plan should be loaded as is, and the whole treatment should be delivered.
<<<

[REQUIREMENT]
UID: RQ-H10TG-247
TYPE: Functional
TITLE: Prevent user from starting an emission due to delta between magnetometers
STATEMENT: >>>
The application shall prevent the user from starting an emission if the delta between the Front Magnetometer and Back Magnetometer correction values is larger than maxMagnetomerDiff. The Front Magnetometer and Back Magnetometer Correction Matrix values will be fetched from the DB.

The MaxMagnetomerDiff should be defined in the machine's HeadConfiguration.
<<<

[REQUIREMENT]
UID: RQ-H10TG-279
TYPE: Functional
TITLE: Quality Assurance - Allow Quality Checks with Dedicated Collimator only
STATEMENT: >>>
The application shall automatically identify that the dedicated QC collimator is connected. It should allow the operator to perform Quality Checks only if this is the connected collimator.
<<<

[REQUIREMENT]
UID: RQ-H10TG-280
TYPE: Functional
TITLE: Quality Assurance - Physics View
STATEMENT: >>>
The application shall provide an interface that enables an authorized user to initiate an emission procedure to measure the quality of the beam.

The user shall be able to select the Applicator type that is used and to set the beam parameters: Energy, Duration.

Once an applicator and Energy are set, the Coils (X, Y, and Focus) and Heater Current that are configured for this Applicator will be populated to the UI.

Refreshing the Physics view shall replace its applicator configurations and physics values
with current database values, remove stale values, and allow the user to retry a failed
refresh.

The application should alert the user if the connected applicator is different from the selected one.

Each requested physics field shall be prepared and emitted separately, and the operator
shall perform a distinct Beam On action for every field.

.. image:: _assets/RQ-H10TG-280.png
<<<

[REQUIREMENT]
UID: RQ-H10TG-281
TYPE: Functional
TITLE: On-Screen Keyboard Adjustable Position
STATEMENT: >>>
The application shall provide the user with the ability to reposition the On-Screen Keyboard on the screen so that it does not block critical interface components.
<<<

[REQUIREMENT]
UID: RQ-H10TG-2
TYPE: Safety
TITLE: Treatment View - Telemetry
STATEMENT: >>>
The application shall provide an interface that displays immutable semantic telemetry
received from the control-board firmware in real time, including:

* Control-board state and firmware mode
* Emission and backup timers
* Emission current and energy
* Safety interlock states, the current required-interlock set, and system-fault categories

The application shall select the telemetry layout from the reported firmware mode. A field
that is not supplied by that firmware mode shall be shown as unavailable rather than as a
false or zero measurement.
<<<

[REQUIREMENT]
UID: RQ-H10TG-3
TYPE: Safety
TITLE: Treatment View - Stop Emission
STATEMENT: >>>
The treatment console shall include a stop control that allows the user to immediately terminate radiation emissions.

.. image:: _assets/RQ-H10TG-3.png
<<<

[REQUIREMENT]
UID: RQ-H10TG-5
TYPE: Safety
TITLE: Treatment View - Emission visible indicator
STATEMENT: >>>
The treatment console shall provide a visible indicator for the entire time the X-rays are produced.

The visual indication of X-ray emission will be provided by a glowing radiation icon Amber color.
<<<

[REQUIREMENT]
UID: RQ-H10TG-36
TYPE: Safety
TITLE: Treatment View - Treatment Plan Execution Condition
STATEMENT: >>>
The application shall prevent treatment plan execution if an interlock is active. The 'Beam-On' button will be disabled.
<<<

[REQUIREMENT]
UID: RQ-H10TG-49
TYPE: Safety
TITLE: Treatment View - Restrict window switching during active emission
STATEMENT: >>>
The application shall temporarily lock the treatment view interface during active radiation delivery.

The left tab bar shall be disabled.
<<<

[REQUIREMENT]
UID: RQ-H10TG-66
TYPE: Safety
TITLE: Quality Assurance - Perform Quality Checks
STATEMENT: >>>
The application shall provide the operator with an interface to test and record the quality of the beam.

Before triggering a QC emission, the operator shall select the energy and one listed QA
emission. The application shall emit and record only the selected item. Performing another
QC emission shall require a new operator selection and activation cycle.

.. image:: _assets/RQ-H10TG-66.png
<<<

[REQUIREMENT]
UID: RQ-H10TG-82
TYPE: Safety
TITLE: Treatment View - Telemetry - No communication to GCB indication
STATEMENT: >>>
The telemetry controls shall show a clear no-communication indication when no valid
telemetry has been received from the GCB for 1.5 seconds. Stale telemetry values shall no
longer be presented as current; affected values shall be shown as unavailable.

.. image:: _assets/RQ-H10TG-82.png
<<<

[REQUIREMENT]
UID: RQ-H10TG-85
TYPE: Safety
TITLE: Treatment View - Patient Details
STATEMENT: >>>
The treatment console shall display details about the treated patient and its treatment site.

The patient details shall include the following:

* Patient full name
* MRN
* Patient DOB
* Field Name
* Dose to be delivered (per fraction)
* Collimator Type (Target Type)
* Field/Shield Size
* Devices
* Setup Notes (Simulation notes)

.. image:: _assets/RQ-H10TG-85.png
<<<

[REQUIREMENT]
UID: RQ-H10TG-86
TYPE: Safety
TITLE: Treatment View - Patient Monitoring
STATEMENT: >>>
The treatment console shall display a live view of the treated patient for monitoring.

The live monitoring will enable the user to stop the emission in case of a patient crisis or movement.

.. image:: _assets/RQ-H10TG-86.png
<<<

[REQUIREMENT]
UID: RQ-H10TG-87
TYPE: Safety
TITLE: Treatment View - Emission audible indicator
STATEMENT: >>>
The application shall provide an audible indicator for the entire time the X-rays are produced.

The indicator should be a plus of half a second on/off with 1 -2 KHz or similar.
<<<

[REQUIREMENT]
UID: RQ-H10TG-91
TYPE: Safety
TITLE: Quality Assurance - Perform System Safety Checks
STATEMENT: >>>
The application shall provide the operator with an interface to test and record system safety features:

The operator will have the controls to prepare and activate the system for radiation. During the radiation, the user will check the:

1. X-ray light - A visual indicator that the X-ray is activated.
2. X-ray sound - An audible indication that the X-ray is activated
3. Door interlock - Open the door and check that the radiation stops.
4. E-stop - Press the physical stop button and check that the radiation stops.
5. Normal stop - Press the applicative stop and ensure the radiation is stopped.
6. Live video stream - Check that the live camera on the radiation head is working and the room is monitored.
7. Live audio stream - Check that the live audio on the device is working.

For each test, the user will toggle the corresponding success/failure button.

.. image:: _assets/RQ-H10TG-91.png
<<<

[REQUIREMENT]
UID: RQ-H10TG-92
TYPE: Safety
TITLE: Quality Assurance - System Safety Checks Reports
STATEMENT: >>>
The application shall provide the operator with an interface to display the history of test results which includes the following system safety features: X-Ray light, X-Ray sound, door interlock, estop, normal stop, live video stream, and live audio stream between the patient and operator.

.. image:: _assets/RQ-H10TG-92-1.png
.. image:: _assets/RQ-H10TG-92-2.png
<<<

[REQUIREMENT]
UID: RQ-H10TG-93
TYPE: Safety
TITLE: Quality Assurance - Quality Checks Reports
STATEMENT: >>>
The application shall provide the operator with an interface displaying the history of quality test results.

The results will include the current and intensity recorded for each requested QA emission.

The operator will be able to filter the results by the applicator type, energy level, and the date the test was performed.

Each saved QC result shall remain associated with its creation information, operator,
applicator and energy configuration, and measured values. The application shall retrieve
results for the selected configuration.

.. image:: _assets/RQ-H10TG-93.png
<<<

[REQUIREMENT]
UID: RQ-H10TG-94
TYPE: Safety
TITLE: Quality Assurance - Quality Checks Reports - Deviation
STATEMENT: >>>
The application shall provide the operator with an interface displaying the history of quality test results.

The results will include the current and the deviation from the referenced test for each test point (Diode) .
<<<

[REQUIREMENT]
UID: RQ-H10TG-96
TYPE: Safety
TITLE: Treatment View - Prevent Treatment if the Daily Safety checks is not completed
STATEMENT: >>>
The application shall prevent treatment if there is no record of safety checks performed on the day of the treatment or if safety checks are not completed.

A safety check is not completed if the following features were not tested or failed: door interlock, e-stop, and normal stop.

The application will display an error pop-up message to the operator stating that the treatment cannot be delivered if the safety checks are not completed.

The pop-up message will be shown when the user presses the Prepare control.
<<<

[REQUIREMENT]
UID: RQ-H10TG-97
TYPE: Safety
TITLE: Treatment View - Alert for uncompleted Daily Safety checks
STATEMENT: >>>
The application shall display a warning pop-up message if the daily safety checks are uncompleted.

The warning message will be displayed if and only if the following features are successfully tested: door interlock, e-stop, and normal stop, and the following features were not tested or failed:

X-Ray light, X-Ray sound, live video stream, and live audio stream.

The application will display a warning pop-up message to the operator asking the user to confirm the treatment even though the safety checks are uncompleted.

The pop-up message will be shown when the user presses the Prepare control.
<<<

[REQUIREMENT]
UID: RQ-H10TG-106
TYPE: Safety
TITLE: Quality Assurance - Perform System Safety Checks - Save Results
STATEMENT: >>>
The application shall provide a control enabling the user to save the safety test results in the database.

.. image:: _assets/RQ-H10TG-106.png
<<<

[REQUIREMENT]
UID: RQ-H10TG-139
TYPE: Safety
TITLE: Treatment View - Safety Interlocks
STATEMENT: >>>
The dedicated interlock pop-up shall show system readiness at the top. System readiness
shall be true if and only if the buffered master-fault input is clear, no system fault is
active, every interlock required by the current firmware state is available and ready, and
the applicator check is ready.

The pop-up shall always show these operator-facing checks:

* E-stops
* Door closed
* Keys
* Applicator

The Applicator check shall render exactly one row. It shall show ``No applicator`` when no
applicator is attached; otherwise, ``Unknown applicator`` when the attached applicator is
not registered in the database; otherwise, ``Incorrect applicator`` when the registered
applicator does not match the treatment plan; otherwise, it shall show ``Applicator`` with
the existing green thumbs-up indication. The three error labels are mutually exclusive and
each makes system readiness false.
E-stops and keys shall normally appear as one summary row each. When either group is not
ready or is unavailable, the pop-up shall disclose the individual base and remote states
below the summary row.

All other interlocks shall be hidden while ready and shown only while in a bad state.
Technical signals shall be presented with operator-facing group names: Robot arm, Cooling
system, Vacuum system, Backup timers, High-voltage system, Control system, and Auxiliary
safety circuit. The Auxiliary safety circuit group shall aggregate spare interlocks 1 and
2. The buffered master-fault input shall be shown as Master fault only when it is the sole
bad interlock. Each active control-board fault shall appear as a separate attention item
using its formatted fault message and a red thumbs-down indication.

The pop-up shall use the application's gray default foreground for body text, with the
existing accent foreground retained for section headings. On the External GUI only, a
Clear Errors button matching the application's existing clear-errors control shall remain
fixed at the bottom of the pop-up when the buffered master-fault input is bad or any
control-board fault is active or latched. Activating the button shall send the clear-faults
command. The button shall be hidden at all other times and shall not
be present on the Internal GUI.

<<<

[REQUIREMENT]
UID: RQ-H10TG-282
TYPE: Safety
TITLE: Treatment - QC Acceptance and Authorized Approval
STATEMENT: >>>
The application shall evaluate the current Quality Control (QC) result for the applicator
and energy configuration required by the treatment plan before treatment preparation.

The application shall apply the configured acceptance criteria to the current and reference
QC results and shall prevent treatment preparation when the required QC evidence is missing
or unacceptable.

An authorized user may approve a QC result after successful authentication. The application
shall persist the approval decision and reject invalid credentials or a locked account without
changing it. Approval credential checks shall neither increment nor reset failed-login attempts.
<<<

[REQUIREMENT]
UID: RQ-H10TG-283
TYPE: Safety
TITLE: Treatment - Prevent a Treatment When There Is No Approved Physics Data
STATEMENT: >>>
The application shall prevent the user from starting clinical emission exposure (treatment) when no approved physics data is available in the system.

When the user presses the prepare button, an error message will pop up with a message such as: 'Treatment cannot be started. Approved physics data is required.'
<<<

[REQUIREMENT]
UID: RQ-H10TG-284
TYPE: Functional
TITLE: Treatment View - Active Fault Information
STATEMENT: >>>
The application shall display the currently latched control-board fault records. Each
record shall show the fault category, formatted message, and the system state and runtime
captured when the fault occurred.

The application shall keep the displayed fault list synchronized with the control board and
shall allow the operator to clear latched fault records.
<<<

[REQUIREMENT]
UID: RQ-H10TG-285
TYPE: Safety
TITLE: Disable Clinical Functions in Calibration Mode
STATEMENT: >>>
When the connected control board reports calibration firmware mode, the application shall
disable the Treatment and Quality Assurance tabs and obscure their content with a message
directing the user to service the device. Non-clinical service, log, and exit functions
shall remain accessible.
<<<

[REQUIREMENT]
UID: RQ-H10TG-13
TYPE: Usability
TITLE: Treatment View - Layout
STATEMENT: >>>
The user shall have an interface through which they can initiate radiation delivery according to a predefined treatment plan.

The interface shall be accessible via a console located outside of the treatment room to ensure safety and compliance with radiation safety regulations.

The layout should include:

1. Patient Identification
2. The plan's treatment fields.
3. The system telemetry: System status, Main timer (in sec), backup timers (T1 & T2) (in sec), Energy (in kV), and Current (in mA).
4. Activation buttons:

   1. Prepare button - which will prepare the system for radiation (i.e., warm-up and loading).
   2. Beam-On/Reset/Clear error - a multi-state control for triggering the emission, resetting timers, and clearing errors.
   3. Stop button - Stops the emission.

5. Interlocks visualization.
6. System Signals
7. Live Camera to monitor the patient.
8. System readiness indicators

.. image:: _assets/RQ-H10TG-13.png
<<<

[REQUIREMENT]
UID: RQ-H10TG-286
TYPE: Functional
TITLE: System Information - Main Control Firmware Version
STATEMENT: >>>
The application shall display the main-control firmware release version reported by the
control board in the System Information dialog.
<<<

[REQUIREMENT]
UID: RQ-H10TG-287
TYPE: Functional
TITLE: Permission-Based Navigation
STATEMENT: >>>
The application shall show clinical functions only when the authenticated user has the
corresponding permission.
<<<

[REQUIREMENT]
UID: RQ-H10TG-288
TYPE: Functional
TITLE: Database Communication Error
STATEMENT: >>>
The application shall notify the operator and log an error when communication with the
database is lost during treatment preparation or emission.
<<<

[[/SECTION]]

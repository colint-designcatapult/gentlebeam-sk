[DOCUMENT]
TITLE: GBSK Main Control Application FW Verification Testing Protocol
UID: DHF-GBSK-0074

[GRAMMAR]
IMPORT_FROM_FILE: @grammar

[[SECTION]]
TITLE: Purpose

[TEXT]
STATEMENT: >>>
This document provides the full test protocol (a full collection of test cases) for the Main Control
Application Firmware for the GBSK 1.0 system.
<<<

[[/SECTION]]

[[SECTION]]
TITLE: Scope

[TEXT]
STATEMENT: >>>
This report contains a detailed test description to conduct verification testing of GBSK 1.0 Main
Control Application Firmware that covers GBSK Main Control Application FW SRS.
<<<

[[/SECTION]]

[[SECTION]]
TITLE: Abbreviations and Definitions

[TEXT]
STATEMENT: >>>
FW
  Firmware

HVPS
  High Voltage Power Supply

SDP
  Software Development Plan

SVP
  Software Verification Plan

SW
  Software
<<<

[[/SECTION]]

[[SECTION]]
TITLE: References

[TEXT]
STATEMENT: >>>
DHF-GBSK-0001, Rev. 1: GBSK SDP

DHF-GBSK-0003, Rev. 1: GBSK SVP

[LINK: DHF-GBSK-0013]

DHF-GBSK-0031, Rev. 1: GBSK Firmware Architecture Description
<<<

[[/SECTION]]

[[SECTION]]
TITLE: Prerequisites

[TEXT]
STATEMENT: >>>
**Pre-Execution Approval**

A Pre-Execution meeting shall take place, and approved by the project manager and QA/RA.

**Objective(s)**

Verify that:

* All software, firmware, hardware, and test equipment version configurations are identified and listed in the test report prior to execution.
* Test personnel is assigned and available.

**Assumptions & Constraints**

None

**Acceptance Criteria**

All objectives met; test execution can start.
<<<

[[/SECTION]]

[[SECTION]]
PREFIX: TC-H1FWMC-
TITLE: Test Protocol

[TEST_CASE]
UID: TC-H1FWMC-153
TITLE: USB - PC Command Processing - Test Case
STATEMENT: >>>
The user can run the boot loading process via GUI and erase the flash memory's space of the firmware application.
<<<
PREREQUISITES: >>>
1. A new version of the firmware application is provided in the USB
2. System is not running anything
<<<
STEPS: >>>
1. Run the boot loading process via the GUI
2. Click the Logs symbol in the left-hand side of screen
3. Check for the new version of the firmware application in the logs
<<<
EXPECTED_BEHAVIOR: >>>
1. Verify the process is working properly to load a new version of the firmware application
2. Verify logs are loaded in the middle of the screen
3. Verify the version is matching with the newly loaded firmware application
<<<
RELATIONS:
- TYPE: Parent
  VALUE: RQ-H1FWMC-49
  ROLE: Verifies

[TEST_CASE]
UID: TC-H1FWMC-154
TITLE: USB - Bootloader Entry - Test Case
STATEMENT: >>>
The user can run the boot loading process via GUI and erase the flash memory's space of the firmware application.
<<<
PREREQUISITES: >>>
1. A new version of the firmware application is provided in the USB
2. System is not running anything
<<<
STEPS: >>>
1. Run the boot loading process via the GUI
2. Click the Logs symbol in the left-hand side of screen
3. Check for the new version of the firmware application in the logs
<<<
EXPECTED_BEHAVIOR: >>>
1. Verify the process is working properly to load a new version of the firmware application
2. Verify logs are loaded in the middle of the screen
3. Verify the version is matching with the newly loaded firmware application
<<<
RELATIONS:
- TYPE: Parent
  VALUE: RQ-H1FWMC-48
  ROLE: Verifies

[TEST_CASE]
UID: TC-H1FWMC-155
TITLE: USB - CRC Flash Erase - Test Case
STATEMENT: >>>
The user can run the boot loading process via GUI and erase the flash memory's space of the firmware application.
<<<
PREREQUISITES: >>>
1. A new version of the firmware application is provided in the USB
2. System is not running anything
<<<
STEPS: >>>
1. Run the boot loading process via the GUI
2. Click the Logs symbol in the left-hand side of screen
3. Check for the erasing activity of the application in the USB
<<<
EXPECTED_BEHAVIOR: >>>
1. Verify the process is working properly to erase the area corresponding to application CRC verification in the USB
2. Verify logs are loaded in the middle of the screen
3. Verify the logs display the activity of the erasing area of the USB
<<<
RELATIONS:
- TYPE: Parent
  VALUE: RQ-H1FWMC-47
  ROLE: Verifies

[[/SECTION]]

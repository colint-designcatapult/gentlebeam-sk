[DOCUMENT]
TITLE: GBSK Main Control Application FW Software Design Document
UID: DHF-GBSK-0069
METADATA:
  COMPONENT: main-control/main

[GRAMMAR]
IMPORT_FROM_FILE: @grammar

[[SECTION]]
TITLE: Purpose

[TEXT]
STATEMENT: >>>
The purpose of this document is to outline the design specifications of the GBSK Main Control Application Firmware.
<<<

[[/SECTION]]

[[SECTION]]
TITLE: Scope

[TEXT]
STATEMENT: >>>
This document describes the design modules and sub-modules of the GBSK Main Control Application Firmware.

The information in this document is derived from the Main Control Application FW SRS, referenced in this document.

\*The term Software applies to both Software and Firmware components.
<<<

[[/SECTION]]

[[SECTION]]
TITLE: Abbreviations and Definitions

[TEXT]
STATEMENT: >>>
FW
  Firmware

MCU
  Microcontroller Unit

PRS
  Product Requirements Specification

SDP
  Software Development Plan

SRS
  Software Requirements Specification

SW
  Software
<<<

[[/SECTION]]

[[SECTION]]
TITLE: Overview

[TEXT]
STATEMENT: >>>
The main control application firmware serves as the main logical control for system operation.

The main control application firmware monitors all the inputs from the various connections on the board hardware. It can also be used to set and control many of the components that the main control board interfaces with. For off the shelf components, the main control application can set/enable the motor controller drivers for cooling system pump and fans, and can enable the ion pump controller.
<<<

[[/SECTION]]

[[SECTION]]
TITLE: References

[TEXT]
STATEMENT: >>>
DHF-GBSK-0001, Rev. 1: GBSK Software Development Plan (SDP)

DHF-GBSK-0003, Rev. 1: GBSK Software Verification Plan (SVP)

DHF-GBSK-0013, Rev. 1: GBSK Main Control Application Software Requirements Specification (SRS)

DHF-GBSK-0031, Rev. 1: GBSK Firmware Architecture Description
<<<

[[/SECTION]]

[[SECTION]]
TITLE: Architecture Overview

[[SECTION]]
TITLE: High Level System Architecture

[TEXT]
STATEMENT: >>>
.. raw:: html

    <pre class="mermaid">
    graph TD

        BootApp[Bootloader App]
        PC[PC Application]

        Interlocks[Interlocks]
        LEDs[LEDs]
        Indicator[Indicator Board]

        Head[Head Board]
        HVPS[HVPS]
        Peltier[Cooler]

        Timers[External Timers]
        Cooling[Cooling]
        Coils[Coils]

        subgraph Main_Control
            SM[State Machine]
            GPIO[GPIO]
            UART[UART]
            I2C[I2C/SPI]
            ADC[Ext ADC/DAC]
            BootFlash[Bootloader / Flash]

            SM --- GPIO
            SM --- UART
            SM --- I2C
            I2C --> ADC
            BootFlash -.- SM
        end

        BootApp --> Main_Control

        PC -->|USB| Main_Control
        PC -->|ETH / LWIP| Main_Control
        Main_Control -->|ETH / LWIP| PC

        GPIO --> Interlocks
        GPIO --> LEDs
        GPIO --> Indicator

        UART --> Head
        UART --> HVPS
        UART --> Peltier

        I2C --> Timers
        ADC --> Cooling
        ADC --> Coils
    </pre>
<<<

[TEXT]
STATEMENT: >>>
.. raw:: html

    <pre class="mermaid">
    graph TD

      %% Top states
      Startup(["Startup"])
      Crash(["Crash<br/>disable HV<br/>disable emission<br/>set outputs to 0<br/>stop cooler/pumps<br/>stop indicators"])

      %% Core states
      Cold(["Cold<br/>disable HV<br/>disable emission<br/>outputs to 0<br/>stop cooling"])
      Conditioning(["Conditioning<br/>verify estops<br/>set heater<br/>start cooling<br/>hold stable target 15 min"])
      Warmup(["Warmup<br/>enable fast warmup<br/>set heater<br/>start cooling"])
      WarmupFault(["Warmup Fault<br/>heater = 0<br/>stop cooling"])

      Fault(["Fault<br/>disable HV<br/>disable emission<br/>shutdown outputs"])
      ColdFault(["Cold Fault<br/>disable HV<br/>outputs to 0"])

      %% Plan pipeline
      Primed[[Primed]]
      Staging[[Staging]]
      Staged[[Staged]]

      %% Execution pipeline
      HVPSCheck(["HVPS Check<br/>disable HV<br/>disable emission"])
      Setup(["Setup<br/>enable HV<br/>set KV / grid / coils"])
      Ready(["Ready<br/>emission disabled"])
      Launching(["Launching<br/>emission disabled"])
      Emission(["Emission<br/>emission enabled"])
      Termination(["Termination<br/>shutdown safely"])

      %% Discharge
      Discharge(["Discharge<br/>HV off<br/>outputs = 0"])

      %% Startup transitions
      Startup --> Cold
      Crash --> Cold

      %% Cold transitions
      Cold -->|PC CONDITION| Conditioning
      Cold -->|PC WARMUP| Warmup
      Cold -->|FAULT| ColdFault
      Cold -->|PC WIPE PLAN| Cold
      Cold -->|PC STOP| Cold

      %% Conditioning
      Conditioning -->|TARGET STABLE 15 MIN| Primed
      Conditioning -->|FAULT| WarmupFault

      %% Warmup
      Warmup -->|HVPS SP REACHED| Primed
      Warmup -->|FAULT| WarmupFault

      WarmupFault --> Cold

      %% Fault handling
      Fault --> Cold
      ColdFault --> Cold

      %% Plan handling
      Primed -->|PC NEW SESSION| Staging
      Staging -->|PC FINISH STAGE| Staged
      Staging -->|PC WIPE PLAN| Cold

      Staged -->|PC RELEASE PLAN| HVPSCheck

      %% HVPS / Setup
      HVPSCheck -->|Check done| Setup
      Setup -->|HVPS SP REACHED| Ready

      %% Ready → emission flow
      Ready -->|PC RELEASE POINT| Launching
      Launching -->|HVPS SP REACHED; non-QC or QC Active acknowledged| Emission

      %% Emission loop
      Emission -->|OP COMPLETE| Ready

      %% Stop / termination
      Ready -->|PC STOP| Termination
      Emission -->|PC STOP| Termination
      Launching -->|PC STOP| Termination

      Termination --> Cold

      %% Discharge path
      Ready -->|PC STANDBY| Discharge
      Discharge --> Cold

    </pre>
<<<

[TEXT]
STATEMENT: >>>
.. raw:: html

    <pre class="mermaid">
    sequenceDiagram
        participant User
        participant Internal_GUI
        participant External_GUI
        participant GUI_Either
        participant Boards
        participant HVPS

        GUI_Either->>Boards: Initialize (startup only)

        alt Conditioning required
            GUI_Either->>Internal_GUI: Conditioning required
            Internal_GUI->>GUI_Either: Condition request
            GUI_Either->>Boards: Condition (setpoint)

            Boards->>HVPS: Ramp heater to conditioning setpoint
            HVPS-->>Boards: Filament feedback (setpoint reached)
            Boards->>HVPS: Ramp heater down to 0
            Boards-->>GUI_Either: Returned to COLD state
        end

        User->>Internal_GUI: Create plan and load
        Internal_GUI->>External_GUI: Send plan information
        External_GUI-->>User: Plan loaded

        User->>External_GUI: Execute treatment (prepare)
        External_GUI->>Boards: Warmup (setpoint)

        Boards->>HVPS: Ramp heater to warmup setpoint
        HVPS-->>Boards: Filament feedback (setpoint reached)
        Boards-->>External_GUI: Warmup complete (PRIMED)

        External_GUI->>Boards: New session command
        Boards-->>External_GUI: Session ID (STAGING)

        External_GUI->>Boards: Send scalar emission info

        External_GUI->>Boards: Stage plan command
        Boards-->>External_GUI: Plan staged (STAGED)

        External_GUI->>Boards: Confirm scalar emission info

        External_GUI->>Boards: Release plan command

        Boards->>HVPS: Ramp HV
        HVPS-->>Boards: HV ramp feedback (HV reached)
        Boards-->>External_GUI: READY state

        External_GUI-->>User: Ready to start emission
        User->>External_GUI: Start emission
        External_GUI->>Boards: Release point command

        Boards->>HVPS: Run one emission
    </pre>
<<<

[[/SECTION]]

[[SECTION]]
TITLE: Main Modules

[TEXT]
STATEMENT: >>>
State Machine - The routine at the heart of the Main Control Firmware operation. It processes queued events from various data sources to change the operating state of the system's functionality.

HVPS monitoring - monitors and controls data to and from the High Voltage Power Supply.

Headboard communication - monitors and controls data via UART to and from the Headboard.

PC Communication - Connects to the PC application receive commands and to transmit telemetry status data. Utilizes LWIP protocol and connects via Ethernet. Bootloader commands are connected by USB

Interlocks - safety switches that must be engaged for the system to operate properly. If any interlock is disengaged at any time, then the system will either not start or enter a fault state. Emission will also be terminated when disengaged. The user will have to correctly engage the interlock and begin again via the PC Application.

Timers - The Main Control has an internal timer and two external timers for redundancy. These timers are engaged during X-Ray emissions and are primarily for safety.

Cooling System Control - The system utilizes cabinet fans, cooling pump to keep the system temperature from exceeding specified limits. Temperature sensors create feedback loop with fan speed adjustment and the system cooling.
<<<

[[/SECTION]]

[[SECTION]]
PREFIX: SW-H1FWMC-
TITLE: Design Items

[DESIGN_ITEM]
UID: SW-H1FWMC-173
TITLE: Manufacturer Hardware Abstraction
STATEMENT: >>>
The firmware integrates source code provided by the manufacturer of the microcontroller unit to interface with various peripherals of the microcontroller. These include functions to interface with the following peripherals of the microcontroller:

- UART serial port
- SPI serial port
- I2C serial port
- GPIO
- Flash memory controller
- Timer peripheral
- Ethernet MAC peripheral
<<<
RELATIONS:
- TYPE: Parent
  VALUE: RQ-H1FWMC-39
  ROLE: Refines

[DESIGN_ITEM]
UID: SW-H1FWMC-174
TITLE: LWIP Middleware
STATEMENT: >>>
The firmware integrates the source code for a middleware library called LWIP. The version of LWIP integrated is version 1.4.1. This middleware serves to help process incoming data from and outgoing data to the Ethernet MAC peripheral, which is used to communicate with the PC. The specific LWIP functionality utilized is the UDP processing. While LWIP can perform TCP communication, only UDP is utilized.

The configuration for used for LWIP in firmware is a static IP address with a fixed MAC address. UDP communication is configured for two fixed ports.
<<<
RELATIONS:
- TYPE: Parent
  VALUE: RQ-H1FWMC-84
  ROLE: Refines

[DESIGN_ITEM]
UID: SW-H1FWMC-175
TITLE: Input Signals
STATEMENT: >>>
The firmware applies the SAME70 hardware debounce/glitch filter to every physical Port C
interlock input and samples:

- Door, base e-stop, and remote e-stop status
- KUKA 1 and KUKA 2 readiness
- Water level, ion-pump, timer 1, timer 2, HVPS, cooler, water-temperature, and watchdog status
- MCU fault, spare interlocks 1 and 2, and buffered master-fault status
- Remote-key and base-key status

Port C bit 17 is not an interlock input and is excluded from sampling.
<<<
RELATIONS:
- TYPE: Parent
  VALUE: RQ-H1FWMC-8
  ROLE: Refines

[DESIGN_ITEM]
UID: SW-H1FWMC-176
TITLE: Output Signals
STATEMENT: >>>
The firmware controls several digital output signals. The functionality for the output signals are as follows:

- LED control for on-board debug LEDs
- Watchdog IC control
- Fault pulse clear signal
- Ion pump enable
- Emission indicator enable
- Timer start signal
- Fan and pump enable signals

The direct-start handler first evaluates the required-interlock readiness check. When the
check passes, it asserts both ``IO_INDICATORS_EN`` and on-board ``IO_LED6`` before queuing
the corresponding HVPS start command. When the check fails, it performs neither action.
The stop handler deasserts both outputs before queuing the corresponding HVPS stop command.
<<<
RELATIONS:
- TYPE: Parent
  VALUE: RQ-H1FWMC-7
  ROLE: Refines
- TYPE: Parent
  VALUE: RQ-H1FWMC-53
  ROLE: Refines

[DESIGN_ITEM]
UID: SW-H1FWMC-177
TITLE: External ADC Communication
STATEMENT: >>>
The firmware communicates with three external ADC IC chips: two ADS7828 chips and one MAX11647 chips. It communicates with all three chips on a singular I2C bus. The external ADC module cycles through each channel on each chip one by one, reading in the values sent by the chips. These values are 'raw ADC' values sent to the system parameter processing for conversion to their corresponding physical units.

The I2C communication with the ADC ICs is performed using the manufacturer provided 'HRI' library or hardware register interface. This HRI library is used to set up interrupt-based communication on the I2C bus instead of having blocking commands wait for completion of writes and reads of the I2C bus which are relatively long in duration compared to the processing speed of the main microcontroller unit.

In case anyone external IC does not respond, the I2C bus is monitored for any NACK values indicating a non-response. The firmware will report a fault if no response is detected from one of the ADC ICs.

The two ADS7828 chips each have 8 channels, while the MAX11647 has two channels. One ADS7828 chip samples the feedback values from the coil control board. The other ADS7828 samples ion pump feedback, temperature sensors, and onboard power supplies. MAX11647 chip samples the ion Repeller monitoring.
<<<
RELATIONS:
- TYPE: Parent
  VALUE: RQ-H1FWMC-54
  ROLE: Refines
- TYPE: Parent
  VALUE: RQ-H1FWMC-66
  ROLE: Refines
- TYPE: Parent
  VALUE: RQ-H1FWMC-83
  ROLE: Refines

[DESIGN_ITEM]
UID: SW-H1FWMC-178
TITLE: External DAC communication
STATEMENT: >>>
The firmware communicates with two external DAC IC chips. It communicates with both chips on a singular SPI bus, but with independent chip select and load signals for each chip. The external DAC module waits for any queued-up requests by the rest of the firmware to write new DAC values. In case multiple DAC values are queued up simultaneous or in quick succession, the DAC module processes them in FIFO (first in first out) fashion, waiting for the SPI bus to be free until the next value is processed.

The DAC module utilizes the manufacturer's hardware abstraction library to write serial data to the SPI bus. The writes to the SPI bus are non-block interrupt-based calls which allows the processor to continue operating during the relatively longer SPI transmission (compared to processing speed). The DAC module utilizes the SPI interrupt handler to set flags for handling the queued DAC requests (indicating bus is free).

In addition to sending data over the SPI bus, the DAC module handles the digital chip select and load signals. These signals are independent for each chip, so there are a total of 4 digital output lines controlled by the DAC via the hardware abstraction library's provided GPIO control.

Each DAC IC controls four separate channels, although on the board only three channels on each DAC IC are utilized. One DAC IC sets the analog voltage for the heatsink fan control, cabinet fan control, and coolant pump motor control. The second DAC IC sets the analog voltage for the X-coil deflection control, Y-coil deflection control, and focus coil control.
<<<
RELATIONS:
- TYPE: Parent
  VALUE: RQ-H1FWMC-55
  ROLE: Refines
- TYPE: Parent
  VALUE: RQ-H1FWMC-63
  ROLE: Refines
- TYPE: Parent
  VALUE: RQ-H1FWMC-65
  ROLE: Refines

[DESIGN_ITEM]
UID: SW-H1FWMC-179
TITLE: Backup Timer Communication
STATEMENT: >>>
The firmware communicates with two external backup timers. It communicates with both timers on a singular I2C bus, with the main microcontroller acting as master to the two slave timers. The timer module alternates between each timer, continuously communicating with the two timers. As the two timers are slave devices, they require the master to initiate communication. The main microcontroller will send commands to the timers which include read time, set timer period, pause counting, and clear timer period. The timers will always report back their timer counter value in response to each command. The 'read time' command is simply for the timer to do nothing other than report the time back.

The I2C communication with the timers is performed using the manufacturer provided 'HRI' library or hardware register interface. This HRI library is used to set up interrupt-based communication on the I2C bus instead of having blocking commands wait for completion of writes and reads of the I2C bus which are relatively long in duration compared to the processing speed of the main microcontroller unit.

In case anyone external IC does not respond, the I2C bus is monitored for any NACK values indicating a non-response. The firmware will report a fault if no response is detected from one of the ADC ICs.
<<<
RELATIONS:
- TYPE: Parent
  VALUE: RQ-H1FWMC-11
  ROLE: Refines
- TYPE: Parent
  VALUE: RQ-H1FWMC-52
  ROLE: Refines
- TYPE: Parent
  VALUE: RQ-H1FWMC-53
  ROLE: Refines

[DESIGN_ITEM]
UID: SW-H1FWMC-180
TITLE: Bootloading and Debug Communication
STATEMENT: >>>
The firmware communicates with the PC via one of the microcontrollers' serial UART interface. The firmware both receives and transmits data on this UART port. Due to the nature of UART having independent transmit and receive lines, the transmit and receive functionality operate independently. As the UART baud rate is relatively slow compared to the processing speed of the microcontroller, both sending and receiving data is performed with non-blocking interrupt callback functions.

Transmitted data is sent as a buffer of bytes, representing a singular data packet to the PC, with the interrupt callback occurring once all data bytes have been transmitted. The firmware sets a flag when transmission is initiated, and clears the flag after transmission is finished, to not create transmission conflicts on the transmit line.

Reception is performed one byte at a time, with the interrupt callback occurring once a data byte is available. The parsing of the received byte is done to determine whether a complete data packet has been received from the PC, as according to the communication protocol. Once a completed data packet has been received, the firmware sets a flag for further data processing outside of the parsing inside of the interrupt callback.

The firmware will monitor for a boot load command from the PC. Once received the firmware will reset the microcontroller into bootloader mode.
<<<
RELATIONS:
- TYPE: Parent
  VALUE: RQ-H1FWMC-47
  ROLE: Refines
- TYPE: Parent
  VALUE: RQ-H1FWMC-48
  ROLE: Refines
- TYPE: Parent
  VALUE: RQ-H1FWMC-49
  ROLE: Refines

[DESIGN_ITEM]
UID: SW-H1FWMC-181
TITLE: Head Interface Board Communication
STATEMENT: >>>
The firmware communicates with the external head interface board via one of the microcontroller's serial UART interfaces. The firmware both receives and transmits data on this UART port. Due to the nature of UART having independent transmit and receive lines, the transmit and receive functionality operate independently. As the UART baud rate is relatively slow compared to the processing speed of the microcontroller, both sending and receiving data is performed with nonblocking interrupt callback functions.

Transmitted data is sent as a buffer of bytes, representing a singular data packet to the PC, with the interrupt callback occurring once all data bytes have been transmitted. The firmware sets a flag when transmission is initiated, and clears the flag after transmission is finished, to not create transmission conflicts on the transmit line.

Reception is performed one byte at a time, with the interrupt callback occurring once a data byte is available. The parsing of the received byte is done to determine whether a complete data packet has been received from the PC, as according to the communication protocol. Once a completed data packet has been received, the firmware sets a flag for further data processing outside of the parsing inside of the interrupt callback.

As transmission on UART is asynchronous both in terms of clock as well as word alignment (within a packet), a 'sync value' is utilized at the start of each packet to help synchronize communication in case of any lost or missing bytes.
<<<
RELATIONS:
- TYPE: Parent
  VALUE: RQ-H1FWMC-2
  ROLE: Refines
- TYPE: Parent
  VALUE: RQ-H1FWMC-3
  ROLE: Refines
- TYPE: Parent
  VALUE: RQ-H1FWMC-62
  ROLE: Refines

[DESIGN_ITEM]
UID: SW-H1FWMC-182
TITLE: HVPS Interface Board Communication
STATEMENT: >>>
The firmware communicates with the external HVPS interface board via one of the microcontroller's serial UART interfaces. The firmware both receives and transmits data on this UART port. Due to the nature of UART having independent transmit and receive lines, the transmit and receive functionality operate independently. As the UART baud rate is relatively slow compared to the processing speed of the microcontroller, both sending and receiving data is performed with nonblocking interrupt callback functions.

Transmitted data is sent as a buffer of bytes, representing a singular data packet to the PC, with the interrupt callback occurring once all data bytes have been transmitted. The firmware sets a flag when transmission is initiated, and clears the flag after transmission is finished, to not create transmission conflicts on the transmit line.

Reception is performed one byte at a time, with the interrupt callback occurring once a data byte is available. The parsing of the received byte is done to determine whether a complete data packet has been received from the PC, as according to the communication protocol. Once a completed data packet has been received, the firmware sets a flag for further data processing outside of the parsing inside of the interrupt callback.

As transmission on UART is asynchronous both in terms of clock as well as word alignment (within a packet), a 'sync value' is utilized at the start of each packet to help synchronize communication in case of any lost or missing bytes.

When processing an HVPS status message that passes checksum validation, the firmware
toggles on-board LED4 once before copying and reporting the received status. The status
processing path does not toggle LED4 again, so repeated valid messages produce a visible
communication-activity blink.
<<<
RELATIONS:
- TYPE: Parent
  VALUE: RQ-H1FWMC-68
  ROLE: Refines

[DESIGN_ITEM]
UID: SW-H1FWMC-183
TITLE: PC Ethernet Communication
STATEMENT: >>>
The firmware communicates with the PC through an Ethernet interface using an RMII
transceiver and the LWIP UDP stack. Application traffic is separated into:

- Commands and their responses
- Unsolicited 100 Hz system-telemetry packets
- Unsolicited 1 Hz device-information packets
- Unsolicited fault-entry and fault-clear notifications

The PC can also request telemetry, device information, and an indexed fault entry. UDP is
used because timely delivery is more important than retransmitting stale real-time data.
Application payloads use the PC-Firmware Communication Protocol framing and CRC described
in the appendix.

During HVPS-interface initialization, the firmware queues command ``0x7F`` to request that
board's release version. The UART receive path recognizes the 13-word ``VRSN`` frame,
validates its additive checksum, and caches the returned 32-byte version field and
operating-mode identifier.

The 19-word PC device-information payload contains the main-control 32-byte release version,
application CRC, and operating mode, followed by the cached HVPS-interface 32-byte release
version and operating mode. Until a valid HVPS version response is received, the cached
version is ``unavailable`` and its operating-mode identifier is invalid.
<<<
RELATIONS:
- TYPE: Parent
  VALUE: RQ-H1FWMC-84
  ROLE: Refines
- TYPE: Parent
  VALUE: RQ-H1FWMC-83
  ROLE: Refines
- TYPE: Parent
  VALUE: RQ-H1FWMC-306
  ROLE: Refines

[DESIGN_ITEM]
UID: SW-H1FWMC-185
TITLE: Fault Handling
STATEMENT: >>>
The firmware maintains a latched table of at most four active fault records. A record
contains the fault category, CRC-32 hash of the format string, clear epoch, entry index,
active count, captured system state, captured runtime, format-argument count, a
NUL-terminated 128-byte printable ASCII format string, and up to five 32-bit arguments.
Format specifiers identify unsigned integer, hexadecimal, floating-point, and literal
percent values so that the CNC can render a human-readable message.

Repeated reports with the same category and format are deduplicated while latched. A new
distinct record is published without waiting for a request. The PC retrieves a coherent
snapshot by requesting entries by index and checking the clear epoch and active count.
An out-of-range index returns an empty entry with the current snapshot metadata.
<<<
RELATIONS:
- TYPE: Parent
  VALUE: RQ-H1FWMC-6
  ROLE: Refines

[DESIGN_ITEM]
UID: SW-H1FWMC-186
TITLE: PC Ethernet Data
STATEMENT: >>>
Each PC Ethernet communication packet contains a synchronization header, packet type,
packet counter, payload length, payload, and CRC footer. PC commands receive corresponding
responses. System telemetry, device information, new fault entries, and fault-clear
updates can also be transmitted without a preceding request. Packet types and payload
schemas are documented in the appendix section PC-Firmware Communication Protocol.
<<<
RELATIONS:
- TYPE: Parent
  VALUE: RQ-H1FWMC-46
  ROLE: Refines
- TYPE: Parent
  VALUE: RQ-H1FWMC-84
  ROLE: Refines

[DESIGN_ITEM]
UID: SW-H1FWMC-187
TITLE: State Machine
STATEMENT: >>>
The firmware uses a state variable and queued events to execute treatment-plan and
emission state transitions. Events originate from PC commands, HVPS stabilization, timers,
and detected faults. Event identifiers outside the valid enumeration are rejected.

Valid events enter a circular FIFO with separate read and write indices and one reserved
slot. The producer and consumer each perform data and index updates inside a critical
section. The producer stores an event before publishing the new write index. The consumer
copies the next event to a local value before advancing the read index, so a concurrently
queued event cannot be partially published, overwritten, or dispatched twice. When the
next write index would equal the read index, the producer leaves the queue unchanged and
latches a ``FAULT_MEMORY`` record with the message ``State machine event queue overflow``.

The processing loop drains accepted events in FIFO order and dispatches each local event
through the function-table entry selected by the current state. The table defaults every
entry to the crash handler before known states are assigned. A state index outside the
table bounds is also routed directly to the crash handler. That handler disables the
high-voltage and emission interlocks, commands HVPS and coil outputs to zero, stops the
coolant pump and external indicators, and sets the system-crash state.
<<<
RELATIONS:
- TYPE: Parent
  VALUE: RQ-H1FWMC-31
  ROLE: Refines
- TYPE: Parent
  VALUE: RQ-H1FWMC-68
  ROLE: Refines
- TYPE: Parent
  VALUE: RQ-H1FWMC-80
  ROLE: Refines
- TYPE: Parent
  VALUE: RQ-H1FWMC-84
  ROLE: Refines

[DESIGN_ITEM]
UID: SW-H1FWMC-188
TITLE: General System Monitoring: Fan Control
STATEMENT: >>>
The firmware periodically evaluates temperature feedback and the current system state to
control cooling outputs. While high voltage can be present from setup through discharge,
the cabinet fan is driven at 4.9 V. Otherwise the cabinet fan uses nominal 30°C, 25°C, and
20°C transition points for 4.9 V, 4.5 V, and 4.1 V operation, with a 3.7 V minimum and
2°C downward hysteresis.

Enabling the coolant pump cancels a pending shutdown, asserts the pump output, and drives
its fan at 1.85 V. A request to disable an active pump keeps the pump and fan operating for
three minutes of post-operation cooling; expiry then deasserts the pump and sets its fan
voltage to zero.

The heatsink fan is adjusted based on heatsink-temperature feedback, with higher
temperatures corresponding to higher fan speeds.
<<<
RELATIONS:
- TYPE: Parent
  VALUE: RQ-H1FWMC-63
  ROLE: Refines
- TYPE: Parent
  VALUE: RQ-H1FWMC-65
  ROLE: Refines

[DESIGN_ITEM]
UID: SW-H1FWMC-189
TITLE: General System Monitoring: System Faults
STATEMENT: >>>
The firmware periodically evaluates measured and reported feedback to detect cooling
faults. Coolant temperature above 35°C and
cabinet temperature above 40°C produce their corresponding temperature fault reports.
Coolant pressure and flow limits are evaluated while the pump is operating; pressure
debounce counters are cleared while it is off so stale samples cannot cause a later fault.

The same monitoring cycle also detects communication timeouts, interlock faults, ion
repeller overcurrent or voltage deviations, and deflection or focus-coil feedback
deviations.
<<<
RELATIONS:
- TYPE: Parent
  VALUE: RQ-H1FWMC-6
  ROLE: Refines
- TYPE: Parent
  VALUE: RQ-H1FWMC-9
  ROLE: Refines
- TYPE: Parent
  VALUE: RQ-H1FWMC-60
  ROLE: Refines
- TYPE: Parent
  VALUE: RQ-H1FWMC-61
  ROLE: Refines
- TYPE: Parent
  VALUE: RQ-H1FWMC-62
  ROLE: Refines
- TYPE: Parent
  VALUE: RQ-H1FWMC-66
  ROLE: Refines

[DESIGN_ITEM]
UID: SW-H1FWMC-190
TITLE: State: Startup
STATEMENT: >>>
The startup state is the initial state of the firmware after device reset. No faults are processed during this state, the system can only exit fault state into cold once an 'initialize' command is received from the PC. The purpose of this state is to allow the PC and other parts of the system, which may have longer power on times, initialize before regular system operation commences.
<<<
RELATIONS:
- TYPE: Parent
  VALUE: RQ-H1FWMC-38
  ROLE: Refines
- TYPE: Parent
  VALUE: RQ-H1FWMC-39
  ROLE: Refines

[DESIGN_ITEM]
UID: SW-H1FWMC-191
TITLE: State: Cold
STATEMENT: >>>
The cold state is for when the system has been initialized, but the filament and high voltage are off. Any faults which occur transition the system into cold fault mode. From cold state, the system can transition to the conditioning state if the PC sends a conditioning command. The firmware can also transition into the warmup state if the PC sends a warmup command.
<<<
RELATIONS:
- TYPE: Parent
  VALUE: RQ-H1FWMC-38
  ROLE: Refines
- TYPE: Parent
  VALUE: RQ-H1FWMC-69
  ROLE: Refines
- TYPE: Parent
  VALUE: RQ-H1FWMC-86
  ROLE: Refines
- TYPE: Parent
  VALUE: RQ-H1FWMC-87
  ROLE: Refines

[DESIGN_ITEM]
UID: SW-H1FWMC-192
TITLE: State: Cold Fault
STATEMENT: >>>
The cold fault state is for when a system error has occurred, but the system does not have the filament running. The firmware can transition out of the cold fault state and into the cold state after receiving a reset fault command from the PC.
<<<
RELATIONS:
- TYPE: Parent
  VALUE: RQ-H1FWMC-33
  ROLE: Refines

[DESIGN_ITEM]
UID: SW-H1FWMC-193
TITLE: State: Conditioning
STATEMENT: >>>
On entry to conditioning, the firmware sets the requested filament current, enables the
coolant pump, and clears the conditioning hold timer. The first indication that the HVPS
filament has reached and stabilized at the target starts a 9,000-deci-second (15-minute)
hold. Later stabilization indications do not restart an active hold. When the timer expires,
the firmware marks it completed before queuing one completion event and transitions to
primed state.

A PC stop returns the system to cold state. A fault during conditioning transitions the
system to warmup-fault state.
<<<
RELATIONS:
- TYPE: Parent
  VALUE: RQ-H1FWMC-33
  ROLE: Refines
- TYPE: Parent
  VALUE: RQ-H1FWMC-34
  ROLE: Refines
- TYPE: Parent
  VALUE: RQ-H1FWMC-35
  ROLE: Refines
- TYPE: Parent
  VALUE: RQ-H1FWMC-36
  ROLE: Refines
- TYPE: Parent
  VALUE: RQ-H1FWMC-37
  ROLE: Refines

[DESIGN_ITEM]
UID: SW-H1FWMC-194
TITLE: State: Warmup
STATEMENT: >>>
The warmup state is for when the system is ramping up the filament current to reach a level where the filament is at a temperature that can sustain lower levels of emission. Due to the nature of the HVPS filament control (constant current) and the system characteristics (increased resistance with increased temperature), and the nature of the filament and cathode sensitivity, it is not advisable to go to a higher current which could sustain the intended target levels of emission output.

Before queuing entry to warmup, the PC command handler requires COLD state, verifies both
emergency-stop inputs, and then validates the target. An open emergency stop produces an
``SPR_ACCESS_ERROR`` response rather than acknowledging a transition that cannot occur.
The state-entry handler verifies the emergency stops again; failure reports an interlock
fault and returns before changing the heater, coolant pump, or state.

Warmup completes once the reported filament value from the HVPS interface board stabilizes at the target filament current. The firmware will transition to primed state once that target setpoint has been reached if no current plan is loaded, otherwise it will transition to the staged state.

If the PC sends a stop command in the warmup state, the firmware will transition back to the cold state. If a fault occurs during the warmup state, the system will instead transition to the warmup fault state.
<<<
RELATIONS:
- TYPE: Parent
  VALUE: RQ-H1FWMC-41
  ROLE: Refines
- TYPE: Parent
  VALUE: RQ-H1FWMC-76
  ROLE: Refines

[DESIGN_ITEM]
UID: SW-H1FWMC-195
TITLE: State: Warmup Fault
STATEMENT: >>>
The warmup fault state is for when a system error has occurred when warming up the filament such as during the conditioning state or the warmup state. The firmware can transition out of the warmup fault state and into the cold state after receiving a reset fault command from the PC.
<<<
RELATIONS:
- TYPE: Parent
  VALUE: RQ-H1FWMC-13
  ROLE: Refines
- TYPE: Parent
  VALUE: RQ-H1FWMC-22
  ROLE: Refines

[DESIGN_ITEM]
UID: SW-H1FWMC-196
TITLE: State: Primed
STATEMENT: >>>
The primed state is for when the filament of the system is at the warmup value, but no plan is loaded, nor has any plan loading been initiated. On an error, the system enters fault state. On a standby event, which can be initiated by the PC or after a timeout, the firmware transitions from primed state to discharge state. If the firmware receives a new session command in primed, it will begin a new session and transition the state into the staging state.
<<<
RELATIONS:
- TYPE: Parent
  VALUE: RQ-H1FWMC-42
  ROLE: Refines

[DESIGN_ITEM]
UID: SW-H1FWMC-197
TITLE: State: Staging
STATEMENT: >>>
The staging state is for when the PC is actively loading the parameters for a new treatment plan. On an error, the system enters fault state. On a standby event, which can be initiated by the PC or after a timeout, the firmware transitions from the staging state to discharge state. If the firmware receives a wipe plan command, it will transition the state back to primed. If the PC sends a command to finalize the staging of the plan, the firmware will transition the state from staging to staged.
<<<
RELATIONS:
- TYPE: Parent
  VALUE: RQ-H1FWMC-27
  ROLE: Refines
- TYPE: Parent
  VALUE: RQ-H1FWMC-28
  ROLE: Refines
- TYPE: Parent
  VALUE: RQ-H1FWMC-32
  ROLE: Refines
- TYPE: Parent
  VALUE: RQ-H1FWMC-40
  ROLE: Refines
- TYPE: Parent
  VALUE: RQ-H1FWMC-43
  ROLE: Refines
- TYPE: Parent
  VALUE: RQ-H1FWMC-44
  ROLE: Refines
- TYPE: Parent
  VALUE: RQ-H1FWMC-45
  ROLE: Refines
- TYPE: Parent
  VALUE: RQ-H1FWMC-82
  ROLE: Refines

[DESIGN_ITEM]
UID: SW-H1FWMC-198
TITLE: State: Staged
STATEMENT: >>>
The staged state is for when the PC has completed loading one scalar emission but has not
yet released it for execution. Before plan release is allowed, the PC must confirm that
emission.

On an error, the system enters fault state. On standby, the firmware transitions to
discharge. A wipe command returns it to primed. A valid plan release after scalar
confirmation transitions the system into the HVPS check state.
<<<
RELATIONS:
- TYPE: Parent
  VALUE: RQ-H1FWMC-26
  ROLE: Refines
- TYPE: Parent
  VALUE: RQ-H1FWMC-74
  ROLE: Refines

[DESIGN_ITEM]
UID: SW-H1FWMC-199
TITLE: State: HVPS Check
STATEMENT: >>>
The HVPS check state is when the main application firmware performs an interlock check with the HVPS interface board. The firmware sends commands to the HVPS interface board indicating that it is going to toggle the interlocks and then toggles the interlocks. This process is to have the HVPS interface board 'unlock' the HVPS functionality to turn on high voltage and control the grid by verifying that interlocks function appropriately and can be toggled. The HVPS interface board will update its status accordingly on whether the unlock sequence was successful.

On a successful HVPS check state after toggling the interlocks, the firmware transitions into the setup state. On an error, the firmware transitions to the fault state.
<<<
RELATIONS:
- TYPE: Parent
  VALUE: RQ-H1FWMC-21
  ROLE: Refines

[DESIGN_ITEM]
UID: SW-H1FWMC-200
TITLE: State: Setup
STATEMENT: >>>
The setup state is for when the firmware is ramping up the high voltage to the intended setpoint for an operational point, as well as setting the backup timers. On an error, the system enters fault state. Otherwise, if the system reaches the target high voltage output for the operational point, the firmware will transition into the ready state. If the PC sends a stop command, the firmware will instead transition to the termination state.
<<<
RELATIONS:
- TYPE: Parent
  VALUE: RQ-H1FWMC-14
  ROLE: Refines
- TYPE: Parent
  VALUE: RQ-H1FWMC-19
  ROLE: Refines
- TYPE: Parent
  VALUE: RQ-H1FWMC-20
  ROLE: Refines

[DESIGN_ITEM]
UID: SW-H1FWMC-201
TITLE: State: Ready
STATEMENT: >>>
The ready state is for when the system has high voltage ramped to the scalar emission
setpoint but has not begun emission. On an error the firmware transitions to fault. A stop
command transitions to termination, and a standby command or timeout transitions to
discharge. Only an explicit point-scope release command from the PC transitions to
launching; there is no automatic release path.
<<<
RELATIONS:
- TYPE: Parent
  VALUE: RQ-H1FWMC-17
  ROLE: Refines
- TYPE: Parent
  VALUE: RQ-H1FWMC-18
  ROLE: Refines

[DESIGN_ITEM]
UID: SW-H1FWMC-202
TITLE: State: Launching
STATEMENT: >>>
The launching state ramps filament current and sets the deflection and focusing coil outputs while
emission remains disabled. For an ordinary emission, reaching the HVPS setpoint permits the
transition to Emission. For a QC-armed emission, the firmware first sends the head-interface
Accumulating command and remains in Launching until the head reports an Active edge. A stale
Complete report cannot satisfy this gate. Head command retries are bounded; a timeout or Error
keeps radiation disabled, sends a Stopped command, reports a QC fault, and transitions through the
normal fault handling. A PC Clear Faults command resets the main QC session and its PC result to
Idle/zero, retransmits Stopped until the head confirms a safe terminal state, and accepts the
head's retained Error state as confirmation that acquisition is no longer active. A PC stop
transitions to Termination.
<<<
RELATIONS:
- TYPE: Parent
  VALUE: RQ-H1FWMC-16
  ROLE: Refines
- TYPE: Parent
  VALUE: RQ-H1FWMC-70
  ROLE: Refines

[DESIGN_ITEM]
UID: SW-H1FWMC-203
TITLE: State: Emission
STATEMENT: >>>
The emission state is when the system is performing radiation emission output. On an
error, the system enters fault state. If the PC sends a stop command, the firmware
transitions to termination so the same remaining time can be reconfirmed and resumed.

When the scalar emission completes without interruption, the firmware always transitions
to discharge. It never returns to setup for another point in the same session.
<<<
RELATIONS:
- TYPE: Parent
  VALUE: RQ-H1FWMC-1
  ROLE: Refines
- TYPE: Parent
  VALUE: RQ-H1FWMC-15
  ROLE: Refines
- TYPE: Parent
  VALUE: RQ-H1FWMC-72
  ROLE: Refines
- TYPE: Parent
  VALUE: RQ-H1FWMC-73
  ROLE: Refines
- TYPE: Parent
  VALUE: RQ-H1FWMC-75
  ROLE: Refines
- TYPE: Parent
  VALUE: RQ-H1FWMC-77
  ROLE: Refines

[DESIGN_ITEM]
UID: SW-H1FWMC-204
TITLE: State: Termination
STATEMENT: >>>
The termination state is for the system to ramp down high voltage and turn off the coil outputs after the termination of a treatment plan or operational point. The termination state, however, maintains the filament current value at the targeted warmup setpoint. On an error, the system enters fault state. Otherwise, once termination of the high voltage is completed, the firmware transitions to the staged state. The firmware transitions to this state as a plan still loaded, even if the loaded treatment plan has already been fully completed.
<<<
RELATIONS:
- TYPE: Parent
  VALUE: RQ-H1FWMC-80
  ROLE: Refines
- TYPE: Parent
  VALUE: RQ-H1FWMC-85
  ROLE: Refines

[DESIGN_ITEM]
UID: SW-H1FWMC-205
TITLE: State: Discharge
STATEMENT: >>>
The discharge state is for the system to turn off both the high voltage and the filament current. On an error, the system enters fault state. On completion of the discharge, the firmware transitions to cold state.
<<<
RELATIONS:
- TYPE: Parent
  VALUE: RQ-H1FWMC-80
  ROLE: Refines
- TYPE: Parent
  VALUE: RQ-H1FWMC-86
  ROLE: Refines

[DESIGN_ITEM]
UID: SW-H1FWMC-206
TITLE: States: Fault Discharge and Fault
STATEMENT: >>>
When a fault is detected from an operating state in which high voltage or filament power
may still be energized, the firmware enters Fault Discharge. Entry disables the
high-voltage interlock, pauses the external timers, disables the emission indicators,
commands the HVPS kV, filament, and grid setpoints to zero, and commands all three coil
outputs to zero. The cabinet fan remains at high speed during this discharge.

Fault Discharge continues until kV feedback is below 4 kV, filament feedback is at or
below 700 mA, and the HVPS warming status is clear. The firmware then enters the latched
Fault state, disables the emission and grid interlocks, and reasserts the zero output
commands. A further fault event during Fault Discharge transitions immediately to Fault.
<<<
RELATIONS:
- TYPE: Parent
  VALUE: RQ-H1FWMC-77
  ROLE: Refines
- TYPE: Parent
  VALUE: RQ-H1FWMC-78
  ROLE: Refines
- TYPE: Parent
  VALUE: RQ-H1FWMC-80
  ROLE: Refines

[DESIGN_ITEM]
UID: SW-H1FWMC-207
TITLE: System Status (Telemetry)
STATEMENT: >>>
The firmware collects monitored values in a system-status array used as the source of truth
for firmware decisions and telemetry serialization. Every 10 ms, it serializes the array
and sends it to the CNC. The telemetry layout appends the raw state-dependent
required-interlock mask and publishes the complete physical and required interlock masks,
head-interface coolant values, buttons, collimator ID, and magnetometer values. Telemetry
requests use the same serializer.
<<<
RELATIONS:
- TYPE: Parent
  VALUE: RQ-H1FWMC-83
  ROLE: Refines

[DESIGN_ITEM]
UID: SW-H1FWMC-208
TITLE: Treatment Session (Scalar Emission)
STATEMENT: >>>
Each treatment session stores exactly one scalar operational point. The point contains
total treatment time, remaining treatment time, high-voltage kV, target emission current
mA, filament current, and X, Y, and focus coil currents. The session contains no point
count, point index, or automatic-execution field.
<<<
RELATIONS:
- TYPE: Parent
  VALUE: RQ-H1FWMC-16
  ROLE: Refines
- TYPE: Parent
  VALUE: RQ-H1FWMC-23
  ROLE: Refines
- TYPE: Parent
  VALUE: RQ-H1FWMC-24
  ROLE: Refines
- TYPE: Parent
  VALUE: RQ-H1FWMC-25
  ROLE: Refines
- TYPE: Parent
  VALUE: RQ-H1FWMC-29
  ROLE: Refines
- TYPE: Parent
  VALUE: RQ-H1FWMC-30
  ROLE: Refines
- TYPE: Parent
  VALUE: RQ-H1FWMC-81
  ROLE: Refines

[DESIGN_ITEM]
UID: SW-H1FWMC-209
TITLE: Backup Timer Data
STATEMENT: >>>
The communication data sent by the main control application firmware are commands which are timer related tasks. These commands are setting the target time, pausing the timer counting and resetting the timer (including the interlock IO used to terminate emissions), as well as a report time request. There is no start command, as start is performed via hardware IO. This is due to the two timer MCUs sharing a single serial communication bus. To ensure that the timer counts are as synchronized as possible, the trigger to start is instead done via a digital signal rather than sequential serial commands. This signal only starts with the count of the timers and cannot stop them.

The communication data from the timers are the reported time value being counted, as well as the state of the timer.

Both received and sent messages use a simple checksum value to check the validity of the message payloads.
<<<
RELATIONS:
- TYPE: Parent
  VALUE: RQ-H1FWMC-10
  ROLE: Refines
- TYPE: Parent
  VALUE: RQ-H1FWMC-53
  ROLE: Refines

[DESIGN_ITEM]
UID: SW-H1FWMC-210
TITLE: Interlock Monitoring
STATEMENT: >>>
The firmware samples and publishes every physical interlock input without applying the
fault mask to the reported status. It derives a separate required-interlock mask from the
compiled firmware mode and current state, publishes that mask in system telemetry, and
compares only those required bits with the sampled input status. A mismatch records an
interlock fault and initiates the existing latched-fault transition. Inputs omitted from
the required mask remain visible for diagnostics but do not independently create an
interlock fault in that state.

Before changing from cold to conditioning, the transition routine verifies both the base
and remote emergency-stop inputs. If either input is open, it reports a
``FAULT_INTERLOCK`` record with the message ``Cannot condition with e-stops open`` and
returns while still cold, before changing the heater command, starting the coolant pump,
or selecting the conditioning state.
<<<
RELATIONS:
- TYPE: Parent
  VALUE: RQ-H1FWMC-8
  ROLE: Refines
- TYPE: Parent
  VALUE: RQ-H1FWMC-25
  ROLE: Refines

[DESIGN_ITEM]
UID: SW-H1FWMC-294
TITLE: Head Interface Board Data
STATEMENT: >>>
In normal firmware, the packet transmitted to the head interface is 12 bytes. Bytes 0 through 7
carry the duplicated indicator LED command and complements. Bytes 8 through 11 independently
carry the duplicated desired QC acquisition state and complements. The QC command is retried at
100 ms intervals for at most one second while the LED command remains independently persistent.
Calibration firmware retains the legacy 8-byte command.

The normal-firmware packet received from the head interface retains the established cooling,
button, collimator-ID, and magnetometer fields and appends unsigned 32-bit QC channel 0 and
channel 1 accumulation sums, their independent sample counts, and the head QC state. Channel 0
contains the analog PC2 diode acquisition. Channel 1 is retained for wire compatibility and is
reported as zero samples, zero accumulation, and disconnected. Main control snapshots the five
values once per valid head packet, forwards them without local re-accumulation, and accepts
Complete only after observing Active for the current session. Calibration firmware retains the
legacy receive layout.
<<<
RELATIONS:
- TYPE: Parent
  VALUE: RQ-H1FWMC-2
  ROLE: Refines
- TYPE: Parent
  VALUE: RQ-H1FWMC-305
  ROLE: Refines

[DESIGN_ITEM]
UID: SW-H1FWMC-295
TITLE: HVPS Interface Board Data
STATEMENT: >>>
The transmitted data to the HVPS interface board are commands to set various output control parameters including grid voltage, filament current, high voltage, and output power. There are also commands to initiate the process to test the high voltage and grid interlocks that the main control board provides to the HVPS interlock board.

The data received from the HVPS interface board are the target setpoint values for, as well as the monitored feedback values from, the HVPS. Additionally, status flags and IO values are reported from the HVPS interface board.
<<<
RELATIONS:
- TYPE: Parent
  VALUE: RQ-H1FWMC-20
  ROLE: Refines
- TYPE: Parent
  VALUE: RQ-H1FWMC-68
  ROLE: Refines
- TYPE: Parent
  VALUE: RQ-H1FWMC-71
  ROLE: Refines

[DESIGN_ITEM]
UID: SW-H1FWMC-296
TITLE: HVPS Monitoring: Faults
STATEMENT: >>>
The firmware will continuously check at periodic intervals, various measured and reported HVPS feedback signals to monitor for faults. If any issues are detected, a fault condition may emerge. The following are monitored conditions for fault reporting:

- kV present when no kV should be present
- kV out of tolerance when kV should be present
- mA present when no mA should be present
- mA out of tolerance when mA should be present
- Filament overcurrent
- Occurrence of timeouts when waiting for HVPS values to stabilize
<<<
RELATIONS:
- TYPE: Parent
  VALUE: RQ-H1FWMC-12
  ROLE: Refines
- TYPE: Parent
  VALUE: RQ-H1FWMC-68
  ROLE: Refines

[DESIGN_ITEM]
UID: SW-H1FWMC-297
TITLE: HVPS Monitoring: Stabilization
STATEMENT: >>>
The firmware will continuously check at periodic intervals, various measured and reported HVPS feedback signals to determine if the HVPS is stable at certain states. This determination of stability allows the progression of the state machine in the following states under the following conditions:

- Completion of the conditioning state by having the filament current reach the target filament current
- Completion of the warmup state by having the filament current reach the target filament current
- Completion of the setup state by having the high voltage reach the target kV
- Completion of the launching state by having the high voltage reach the target filament current
- Completion of the discharge state by having low high voltage and filament current
- Completion of the termination state by having low high voltage
<<<
RELATIONS:
- TYPE: Parent
  VALUE: RQ-H1FWMC-21
  ROLE: Refines
- TYPE: Parent
  VALUE: RQ-H1FWMC-71
  ROLE: Refines

[DESIGN_ITEM]
UID: SW-H1FWMC-298
TITLE: Fault Clearing
STATEMENT: >>>
The main control board has hardware which latches fault conditions and disables interlocks
so that emission is safely terminated and cannot be resumed until action is taken by the
firmware. After the PC directive identifier and confirmation match for a clear-fault
request, the directive handler queues both the main-control clear-fault state-machine event
and an HVPS clear-fault command with zero-valued parameters. This directive has no state
gate. The handler leaves the PC directive response as successful without waiting for an
HVPS response; a confirmation mismatch returns an invalid response and queues neither
action.

The state-machine event pulses the hardware clear output, increments the software clear
epoch, empties the latched fault-record table, clears the software category flags, and
publishes an empty fault update. The firmware cannot override an active hardware fault; any
remaining condition re-latches the interlocks and can create a new software fault record.
<<<
RELATIONS:
- TYPE: Parent
  VALUE: RQ-H1FWMC-78
  ROLE: Refines
- TYPE: Parent
  VALUE: RQ-H1FWMC-79
  ROLE: Refines

[DESIGN_ITEM]
UID: SW-H1FWMC-299
TITLE: External Watchdog
STATEMENT: >>>
The main control board contains an external watchdog IC which can terminate emission. The firmware must send a periodically toggle digital output signal and reset the watchdog IC at least once per second, or the watchdog IC will terminate the emission.
<<<
RELATIONS:
- TYPE: Parent
  VALUE: RQ-H1FWMC-10
  ROLE: Refines

[DESIGN_ITEM]
UID: SW-H1FWMC-300
TITLE: Emission Magnetometer Fault Monitoring
STATEMENT: >>>
Setting the coils resets a three-sample magnetometer collector. Valid head-interface
packets fill the collector, and emission entry averages each of the six axes. If three
post-coil samples are unavailable, ``FAULT_MAGNETOMETER`` is reported and emission remains
disabled.

During emission, every valid head-interface packet is evaluated against the stored
baseline. Each axis of both magnetometers is monitored independently. The permitted
deviation is ten percent of the baseline magnitude, but is never less than 1.0 uT to avoid
false faults when a baseline is close to zero.

The firmware tracks consecutive out-of-range readings separately for every axis. An
in-range reading resets the count for that axis without affecting the other axes. A
magnetometer fault is reported when the same axis remains outside its permitted range for
three consecutive packets. A non-finite reading is considered invalid and reports a fault
immediately without waiting for additional packets.

The fault report identifies the affected magnetometer and axis and, when applicable,
includes the measured value, baseline, and permitted deviation. Reporting the fault
invalidates the stored baseline and requests a state-machine transition to the fault state.
<<<
RELATIONS:
- TYPE: Parent
  VALUE: RQ-H1FWMC-307
  ROLE: Refines
- TYPE: Parent
  VALUE: RQ-H1FWMC-77
  ROLE: Refines

[[/SECTION]]

[[/SECTION]]

[DOCUMENT]
TITLE: GBSK Main Control Application FW Software Requirements Specification
UID: DHF-GBSK-0013
METADATA:
  COMPONENT: main-control/main

[GRAMMAR]
IMPORT_FROM_FILE: @grammar

[[SECTION]]
TITLE: Purpose

[TEXT]
STATEMENT: >>>
The purpose of this document is to provide Software Requirements Specifications for the GBSK Main Control
Application Firmware (FW).
<<<

[[/SECTION]]

[[SECTION]]
TITLE: Scope

[TEXT]
STATEMENT: >>>
This document describes all requirements of the GBSK Main Control Application FW.
The information in this document has been derived from the VoxelRay GBSK Product Requirements
Specification, as referenced in this document.

*The term Software applies to both Software and Firmware systems.*
<<<

[[/SECTION]]

[[SECTION]]
TITLE: Abbreviations and Definitions

[TEXT]
STATEMENT: >>>
+-------------------+---------------------------------------------+
| Abbreviation/Term | Definition                                  |
+===================+=============================================+
| FW                | Firmware                                    |
+-------------------+---------------------------------------------+
| HVPS              | High Voltage Power Supply                   |
+-------------------+---------------------------------------------+
| LED               | Light Emitting Diode                        |
+-------------------+---------------------------------------------+
| MCU               | Microcontroller Unit                        |
+-------------------+---------------------------------------------+
| PID               | Proportional Integral Derivative controller |
+-------------------+---------------------------------------------+
| PRS               | Product Requirements Specification          |
+-------------------+---------------------------------------------+
| SDP               | Software Development Plan                   |
+-------------------+---------------------------------------------+
| SRS               | Software Requirements Specification         |
+-------------------+---------------------------------------------+
| SW                | Software                                    |
+-------------------+---------------------------------------------+
<<<

[[SECTION]]
PREFIX: RQ-H1FWMC-
TITLE: Requirements

[REQUIREMENT]
UID: RQ-H1FWMC-1
TYPE: Functional
TITLE: Operation 11: Termination - PC Stop Command
STATEMENT: >>>
The firmware shall terminate an ongoing emission upon receipt of a stop command from
the PC
<<<

[REQUIREMENT]
UID: RQ-H1FWMC-2
TYPE: Functional
TITLE: Head Interface - IO Feedback
STATEMENT: >>>
The firmware shall be able to receive IO feedback values from the head interface board
including button press toggles
<<<

[REQUIREMENT]
UID: RQ-H1FWMC-3
TYPE: Functional
TITLE: Head Interface - Communication Monitoring
STATEMENT: >>>
The firmware shall monitor communication with the head interface board and report a
fault if no valid communication is received within 0.5 seconds
<<<

[REQUIREMENT]
UID: RQ-H1FWMC-6
TYPE: Functional
TITLE: Fault information - Active Fault Reporting
STATEMENT: >>>
The firmware shall retain and report up to four simultaneously active fault records. In
response to an indexed fault-information request from the PC, the firmware shall report:

- The fault category
- A printable fault-message format string and its checksum
- Up to five raw format arguments
- The system state and runtime captured when the fault was first reported
- The fault-clear epoch, requested entry index, and total active-fault count

The firmware shall suppress duplicate records for the same fault category and message
format while the record remains latched. Newly detected distinct records shall also be
published without a request from the PC.
<<<

[REQUIREMENT]
UID: RQ-H1FWMC-7
TYPE: Safety
TITLE: Emission indicator
STATEMENT: >>>
The firmware shall enable the external emission indicators only after all required safety
interlocks permit an accepted emission-start request, keep them enabled while emission is
ongoing, and disable them when emission is stopped.
<<<

[REQUIREMENT]
UID: RQ-H1FWMC-8
TYPE: Safety
TITLE: Interlocks
STATEMENT: >>>
The firmware shall monitor every physical Port C interlock input and throw a fault when an
interlock required by the compiled firmware mode and current system state is not in its
good condition. Inputs not required in the current state shall remain monitored and
reported.

The firmware shall prevent progression toward energization while either required
emergency-stop interlock is open and shall report an interlock fault. Interlocks include:

- Door, base e-stop, and remote e-stop
- KUKA 1 and KUKA 2 readiness
- Water level, water temperature, ion pump, cooler, and HVPS readiness
- Backup timer 1, backup timer 2, and watchdog readiness
- Remote key and base key
- MCU fault, spare interlocks 1 and 2, and buffered master-fault diagnostic inputs
<<<

[REQUIREMENT]
UID: RQ-H1FWMC-9
TYPE: Safety
TITLE: Coils - Focus Coil Feedback Monitoring
STATEMENT: >>>
The firmware shall monitor the focus coil feedback current values and report a fault for
values that are more than 150 mA out of tolerance.
<<<

[REQUIREMENT]
UID: RQ-H1FWMC-10
TYPE: Safety
TITLE: Backup Timer Communication Integrity
STATEMENT: >>>
The firmware shall monitor the backup timer communication and report a fault if the
communication has been corrupted
<<<

[REQUIREMENT]
UID: RQ-H1FWMC-11
TYPE: Safety
TITLE: Backup Timer Response Monitoring
STATEMENT: >>>
The firmware shall monitor communication with the backup timers and report a fault if
the timers do not respond
<<<

[REQUIREMENT]
UID: RQ-H1FWMC-12
TYPE: Functional
TITLE: Operation 01: Filament conditioning - Target Timeout
STATEMENT: >>>
The firmware shall report a fault if the HVPS has not reached the target filament current
setpoint during the conditioning procedure within a timeout period of 15 seconds
<<<

[REQUIREMENT]
UID: RQ-H1FWMC-13
TYPE: Functional
TITLE: Operation 02: Warmup procedure - Target Timeout
STATEMENT: >>>
The firmware shall report a fault if the HVPS has not reached the target filament setpoint
during the warmup procedure within a timeout period of 15 seconds
<<<

[REQUIREMENT]
UID: RQ-H1FWMC-14
TYPE: Functional
TITLE: Operation 07: Operational point setup - Target kV Timeout
STATEMENT: >>>
The firmware shall report a fault if the HVPS has not reached the target kV setpoint during
the operational point setup processes within a timeout period of 90 seconds
<<<

[REQUIREMENT]
UID: RQ-H1FWMC-15
TYPE: Safety
TITLE: Operation 10 - Emission - High-Voltage Monitoring
STATEMENT: >>>
During an emission, the firmware shall monitor the high voltage feedback from the HVPS
and report a fault if it deviates by more than 5% from the desired target specified in the
treatment plan.
<<<

[REQUIREMENT]
UID: RQ-H1FWMC-16
TYPE: Functional
TITLE: Operation 09: Initiation - Filament Current Ramp
STATEMENT: >>>
On the initiation of an operational point emission execution, the firmware shall direct the
HV interface board to ramp up the filament current to the specified setpoint in the
treatment plan prior to allowing emission (dropping the grid).
For an armed QC session, radiation shall remain disabled until the head acknowledges
Active. Missing acknowledgment within 1 second or an Error response shall command
Stopped and report a QC fault. Clear Faults shall reset the QC response to Idle with
zero accumulations and sample counts, clear the session fault latch, and retransmit
Stopped until the head acknowledges Stopped, Complete, or its retained Error state.
A stale Active report after clearing shall not permit radiation.
<<<

[REQUIREMENT]
UID: RQ-H1FWMC-17
TYPE: Functional
TITLE: Operation 08: Ready - Explicit Emission Release
STATEMENT: >>>
Whenever the firmware enters the ready state for an initial or resumed emission, it shall
remain non-emitting until the PC sends an explicit point-scope release command. The
firmware shall not automatically release an emission.
<<<

[REQUIREMENT]
UID: RQ-H1FWMC-18
TYPE: Functional
TITLE: Operation 08: Ready - Single-Point Session Completion
STATEMENT: >>>
Each treatment session shall contain one operational point. Completion of that point shall
end the session through discharge; the firmware shall not prepare another point within the
same session.
<<<

[REQUIREMENT]
UID: RQ-H1FWMC-19
TYPE: Functional
TITLE: Operation 07: Operational point setup - Target kV Verification
STATEMENT: >>>
Prior to the execution of an operational point emission, the firmware shall verify that the
HV ramping of the HVPS has terminated and the target kV has been reached
<<<

[REQUIREMENT]
UID: RQ-H1FWMC-20
TYPE: Functional
TITLE: Operation 07: Operational point setup - Target kV Command
STATEMENT: >>>
Prior to the execution of a treatment plan operational point emission, the firmware shall
direct the HV interface board to the targeted kV setpoint
<<<

[REQUIREMENT]
UID: RQ-H1FWMC-21
TYPE: Functional
TITLE: Operation 06 - HVPS Check
STATEMENT: >>>
On the release of treatment plan for execution, the firmware shall cycle the HVPS
interlocks and notify the HV interface board
<<<

[REQUIREMENT]
UID: RQ-H1FWMC-22
TYPE: Functional
TITLE: Operation 02: Warmup procedure - Invalid Request Format
STATEMENT: >>>
The firmware shall respond to an invalid warmup procedure request from the PC with an
error reply indicating invalid values have been received. Invalid parameters are those
which cannot be processed or are formatted improperly
<<<

[REQUIREMENT]
UID: RQ-H1FWMC-23
TYPE: Functional
TITLE: Treatment plan reporting - Indexless Query
STATEMENT: >>>
The firmware shall return the scalar operational point parameters for an indexless query.
Indexed operational-point query payloads shall be rejected by strict packet-length
validation.
<<<

[REQUIREMENT]
UID: RQ-H1FWMC-24
TYPE: Functional
TITLE: Operation 04: Treatment plan confirmation - Uninterrupted Parameter Match
STATEMENT: >>>
The firmware shall not consider a treatment plan confirmed until its singular operational
point is confirmed without interruption by a standby timeout or system fault. The point is
confirmed only when the received scalar parameters match the staged parameters.
<<<

[REQUIREMENT]
UID: RQ-H1FWMC-25
TYPE: Functional
TITLE: Operation 05: Treatment plan release - Interlock Readiness
STATEMENT: >>>
The firmware shall not proceed with the release of a treatment plan for execution if all
interlocks are not ready for emission
<<<

[REQUIREMENT]
UID: RQ-H1FWMC-26
TYPE: Functional
TITLE: Operation 05: Treatment plan release - Request State Validation
STATEMENT: >>>
The firmware shall respond to invalid treatment plan release request from the PC with an
error reply indicating an invalid request. A treatment plan release request will be
considered invalid if the system is not in the staged state with a confirmed treatment plan.
<<<

[REQUIREMENT]
UID: RQ-H1FWMC-27
TYPE: Functional
TITLE: Operation 04: Treatment plan confirmation - Incorrect Parameter Values
STATEMENT: >>>
The firmware shall respond to incorrect treatment plan operational point confirmation
parameters from the PC with an error reply indicating incorrect values have been received.
Incorrect parameters are values which do not match staged parameters
<<<

[REQUIREMENT]
UID: RQ-H1FWMC-28
TYPE: Functional
TITLE: Operation 04: Treatment plan confirmation - Invalid Parameter Format
STATEMENT: >>>
The firmware shall respond to invalid treatment plan operational point confirmation
parameters from the PC with an error reply indicating invalid values have been received.
Invalid parameters are those which cannot be processed or are formatted improperly
<<<

[REQUIREMENT]
UID: RQ-H1FWMC-29
TYPE: Functional
TITLE: Operation 04: Treatment plan confirmation - Parameter Range Validation
STATEMENT: >>>
The firmware shall reject treatment parameters that fall outside the configured acceptable
operating ranges.
<<<

[REQUIREMENT]
UID: RQ-H1FWMC-30
TYPE: Functional
TITLE: Operation 04: Treatment plan confirmation - Valid Parameter Acknowledgment
STATEMENT: >>>
The firmware shall acknowledge valid treatment parameters received from the PC. A valid
request shall contain the supported acceleration-potential, emission-current, delivery-time,
beam-optics, and filament-current parameters within their configured operating ranges.
<<<

[REQUIREMENT]
UID: RQ-H1FWMC-31
TYPE: Functional
TITLE: Operation 04: Treatment plan confirmation - Confirmation Timing
STATEMENT: >>>
The firmware shall accept confirmation of the singular scalar operational point after
staging completes and shall return an error if confirmation is attempted outside that
process.
<<<

[REQUIREMENT]
UID: RQ-H1FWMC-32
TYPE: Functional
TITLE: Operation 03.1: Treatment staging - new session commencement - Session Creation
STATEMENT: >>>
The firmware shall accept an argument-free new-session command while in the primed state,
create storage for exactly one scalar operational point, and return a generated session ID
to the PC.
<<<

[REQUIREMENT]
UID: RQ-H1FWMC-33
TYPE: Functional
TITLE: Operation 01: Filament conditioning - Cold-State Restriction
STATEMENT: >>>
The firmware shall only be able to perform filament conditioning from a 'cold' state
where there is no filament current present, and shall reply to filament condition requests
outside of this cold state with an error response
<<<

[REQUIREMENT]
UID: RQ-H1FWMC-34
TYPE: Functional
TITLE: Operation 01: Filament conditioning - Invalid Target Format
STATEMENT: >>>
The firmware shall respond to an invalid filament target value in a filament conditioning
request from the PC with an invalid value response. Invalid parameters are those which
cannot be processed or are formatted improperly.
<<<

[REQUIREMENT]
UID: RQ-H1FWMC-35
TYPE: Functional
TITLE: Operation 01: Filament conditioning - Target Range Validation
STATEMENT: >>>
The firmware shall reject a filament-conditioning target outside the configured acceptable
range.
<<<

[REQUIREMENT]
UID: RQ-H1FWMC-36
TYPE: Functional
TITLE: Operation 01: Filament conditioning - PC-Requested Conditioning
STATEMENT: >>>
The firmware shall be able to perform the filament conditioning as a response to a PC
request, which specifies the target filament current
<<<

[REQUIREMENT]
UID: RQ-H1FWMC-37
TYPE: Functional
TITLE: Operation 01: Filament conditioning - Target Ramp and Hold
STATEMENT: >>>
The firmware shall ramp the filament current to the requested conditioning target and
maintain the stable target for a prescribed conditioning period before completing the
procedure.
<<<

[REQUIREMENT]
UID: RQ-H1FWMC-38
TYPE: Functional
TITLE: Operation 00: Startup - Initialization Transition
STATEMENT: >>>
The firmware shall transition out of the startup state once it receives an initialize
command from the PC, and enter the cold state
<<<

[REQUIREMENT]
UID: RQ-H1FWMC-39
TYPE: Functional
TITLE: Operation 00: Startup - Power-On State
STATEMENT: >>>
The firmware shall begin in a startup state on board power on
<<<

[REQUIREMENT]
UID: RQ-H1FWMC-40
TYPE: Functional
TITLE: Operation 03.1: Treatment staging - new session commencement - Request Validation
STATEMENT: >>>
The firmware shall reject malformed or unsupported staging-session requests.
<<<

[REQUIREMENT]
UID: RQ-H1FWMC-41
TYPE: Functional
TITLE: Operation 02: Warmup procedure - Target Range Validation
STATEMENT: >>>
The firmware shall reject a warmup target outside the configured acceptable range.
<<<

[REQUIREMENT]
UID: RQ-H1FWMC-42
TYPE: Functional
TITLE: Operation 03.1: Treatment staging - new session commencement - Primed-State Restriction
STATEMENT: >>>
The firmware shall be able to begin treatment plan staging only from the primed state,
responding with an error message if establishment of a new staging session is attempted outside of this state
<<<

[REQUIREMENT]
UID: RQ-H1FWMC-43
TYPE: Functional
TITLE: Operation 03.2: Treatment staging - Staging Process Restriction
STATEMENT: >>>
The firmware shall only accept the loading of a treatment plan from the PC during a
designated staging process, responding to the GUI with an error value if the treatment
plan loading is attempted outside of this staging process
<<<

[REQUIREMENT]
UID: RQ-H1FWMC-44
TYPE: Functional
TITLE: Operation 03.2: Treatment staging - Invalid Parameter Format
STATEMENT: >>>
The firmware shall respond to invalid treatment plan staging parameters from the PC with an error reply indicating invalid values have been received. Invalid values are values which cannot be processed, or which are formatted incorrectly
<<<

[REQUIREMENT]
UID: RQ-H1FWMC-45
TYPE: Functional
TITLE: Operation 03.2: Treatment staging - Parameter Range Validation
STATEMENT: >>>
The firmware shall respond to out of bounds treatment plan staging parameters from the
PC with an error reply indicating out of bounds values have been received. An out of
bounds parameter is outside of the range of acceptable values
<<<

[REQUIREMENT]
UID: RQ-H1FWMC-46
TYPE: Functional
TITLE: PC Ethernet commands - Unrecognized Command Handling
STATEMENT: >>>
The firmware shall respond with an 'unrecognized message' response when it receives a
command which is either not formatted properly or not recognized.
<<<

[REQUIREMENT]
UID: RQ-H1FWMC-47
TYPE: Functional
TITLE: USB - CRC Flash Erase
STATEMENT: >>>
The firmware shall be able to erase a predetermined area of flash memory, corresponding to application CRC verification area when requested by the PC over USB.
<<<

[REQUIREMENT]
UID: RQ-H1FWMC-48
TYPE: Functional
TITLE: USB - Bootloader Entry
STATEMENT: >>>
The firmware shall be able to jump to execution of the bootloader application when
requested by the PC over USB.
<<<

[REQUIREMENT]
UID: RQ-H1FWMC-49
TYPE: Functional
TITLE: USB - PC Command Processing
STATEMENT: >>>
The main control application firmware shall be able to receive and process commands
from PC via the board's USB connection.
<<<

[REQUIREMENT]
UID: RQ-H1FWMC-52
TYPE: Functional
TITLE: Backup Timer - Countdown Reporting
STATEMENT: >>>
The firmware shall have the ability to read and report the current backup timer countdown value.
<<<

[REQUIREMENT]
UID: RQ-H1FWMC-53
TYPE: Functional
TITLE: Backup Timer - Initialization
STATEMENT: >>>
The firmware shall have the ability to set and initialize the backup timer ICs.
<<<

[REQUIREMENT]
UID: RQ-H1FWMC-54
TYPE: Safety
TITLE: Coils - Deflection Coil Feedback Monitoring
STATEMENT: >>>
The firmware shall monitor the deflection coil feedback current values and report a fault
for values that are more than 50 mA out of tolerance from the expected setpoint output
<<<

[REQUIREMENT]
UID: RQ-H1FWMC-55
TYPE: Functional
TITLE: Coils - Setpoint Control
STATEMENT: >>>
The firmware shall be able to set the deflection and focus coil setpoint control signals.
<<<

[REQUIREMENT]
UID: RQ-H1FWMC-60
TYPE: Safety
TITLE: Coolant monitoring - Temperature
STATEMENT: >>>
The firmware shall monitor the reported coolant temperature and report a fault if the
temperature is above 35C
<<<

[REQUIREMENT]
UID: RQ-H1FWMC-61
TYPE: Safety
TITLE: Coolant monitoring - Flow Rate
STATEMENT: >>>
The firmware shall monitor the reported coolant system flow rate and report a fault if the
rate is below 2 LPM or above 6 LPM when the coolant pump is enabled.
<<<

[REQUIREMENT]
UID: RQ-H1FWMC-62
TYPE: Functional
TITLE: Head Interface
STATEMENT: >>>
The firmware shall be able to receive cooling system feedback values from the head
interface board.
<<<

[REQUIREMENT]
UID: RQ-H1FWMC-63
TYPE: Functional
TITLE: Temperature monitoring - Heatsink Fan Control
STATEMENT: >>>
The firmware shall adjust the heatsink fan speed based on the heatsink temperature
feedback in order to provide additional cooling when temperatures increase.
<<<

[REQUIREMENT]
UID: RQ-H1FWMC-65
TYPE: Functional
TITLE: Cooling control
STATEMENT: >>>
The firmware shall adjust the system cabinet fan speed from temperature feedback, maintain
coolant circulation for a bounded post-operation cooldown, and avoid stale pressure
measurements when evaluating cooling faults.
<<<

[REQUIREMENT]
UID: RQ-H1FWMC-66
TYPE: Safety
TITLE: Temperature monitoring - Cabinet Temperature Limit
STATEMENT: >>>
The firmware shall report a fault when the system cabinet temperature exceeds the
configured high-temperature safety limit.
<<<

[REQUIREMENT]
UID: RQ-H1FWMC-68
TYPE: Safety
TITLE: HVPS Interface Communication
STATEMENT: >>>
The firmware shall monitor communication with the HVPS interface board, report a fault when
communication is lost, and provide a visual indication of communication activity.
<<<

[REQUIREMENT]
UID: RQ-H1FWMC-69
TYPE: Functional
TITLE: Operation 12: Discharge - Primed-State Timeout
STATEMENT: >>>
The firmware shall return the system into a cold state if the system has been idle in primed
state for a period of 5 minutes.
<<<

[REQUIREMENT]
UID: RQ-H1FWMC-70
TYPE: Functional
TITLE: Operation 09: Initiation - Coil Setpoints
STATEMENT: >>>
The firmware shall set the deflection coil and focus coil outputs to the target setpoint
values from the treatment plan, prior to the start of each operational point emission
<<<

[REQUIREMENT]
UID: RQ-H1FWMC-71
TYPE: Safety
TITLE: Undesired emission monitoring
STATEMENT: >>>
The firmware shall monitor the cathode current feedback from the HVPS and report a fault
if the value is above 0.3 mA when the system is not in 'Emission' state
<<<

[REQUIREMENT]
UID: RQ-H1FWMC-72
TYPE: Functional
TITLE: Operation 10 - Emission - Backup Timer Start
STATEMENT: >>>
When an emission begins, the firmware shall transmit a starting condition to the two
backup timers.
<<<

[REQUIREMENT]
UID: RQ-H1FWMC-73
TYPE: Functional
TITLE: Operation 10 - Emission - Delivery Timer Start
STATEMENT: >>>
When an emission begins, the firmware shall begin an internal timer to serve as the
treatment point delivery duration.
<<<

[REQUIREMENT]
UID: RQ-H1FWMC-74
TYPE: Functional
TITLE: Operation 05: Treatment plan release - Confirmed Plan Release
STATEMENT: >>>
The firmware shall, on request from the PC, release a treatment plan from the staged
state for execution, if a treatment plan has been successfully staged and confirmed
<<<

[REQUIREMENT]
UID: RQ-H1FWMC-75
TYPE: Safety
TITLE: Operation 10 - Emission - Cathode Current Monitoring
STATEMENT: >>>
During an emission, the firmware shall monitor the cathode current feedback from the
HVPS and report a fault if it deviates by more than 5% from the desired target specified in
the treatment plan.
<<<

[REQUIREMENT]
UID: RQ-H1FWMC-76
TYPE: Functional
TITLE: Operation 02: Warmup procedure - Initiation Conditions
STATEMENT: >>>
The firmware shall start warmup from COLD only when the PC supplies a configured valid
target and all required safety interlocks permit operation.
<<<

[REQUIREMENT]
UID: RQ-H1FWMC-77
TYPE: Safety
TITLE: Fault mode - Emission Termination and Safe Discharge
STATEMENT: >>>
The firmware shall terminate any ongoing emission when a fault is detected, command
energized outputs to a safe condition, and complete the required discharge before entering
the latched fault state.
<<<

[REQUIREMENT]
UID: RQ-H1FWMC-78
TYPE: Functional
TITLE: Fault information - Fault Clearing
STATEMENT: >>>
When the firmware accepts a PC clear-fault directive, it shall request that the HVPS clear
its faults, clear the main-control latched fault information, and report the result to the
PC.
<<<

[REQUIREMENT]
UID: RQ-H1FWMC-79
TYPE: Functional
TITLE: Fault information - Fault Latching
STATEMENT: >>>
The firmware shall latch fault category flags and detailed fault records until they are
cleared by the PC, even when the condition that caused a record is no longer present.
<<<

[REQUIREMENT]
UID: RQ-H1FWMC-80
TYPE: Functional
TITLE: Fault mode - Safe State Handling
STATEMENT: >>>
The firmware shall enter safe fault handling when a fault or internal control-processing
failure is detected and shall prevent unsafe state progression.
<<<

[REQUIREMENT]
UID: RQ-H1FWMC-81
TYPE: Functional
TITLE: Treatment plan reporting - Programmed Parameter Query
STATEMENT: >>>
The firmware shall return the currently programmed scalar treatment parameters in response
to a valid PC query.
<<<

[REQUIREMENT]
UID: RQ-H1FWMC-82
TYPE: Functional
TITLE: Operation 03.2: Treatment staging - Scalar Treatment Point Loading
STATEMENT: >>>
The firmware shall accept one scalar treatment point containing the supported
acceleration-potential, emission-current, delivery-time, beam-optics, and filament-current
parameters when they are within their configured operating ranges.
<<<

[REQUIREMENT]
UID: RQ-H1FWMC-83
TYPE: Functional
TITLE: Report telemetry to PC
STATEMENT: >>>
The firmware shall transmit monitored system parameter values to the PC as unsolicited UDP
telemetry packets every 10 ms (100 Hz) and in response to a telemetry request from the PC.
The telemetry parameter layout shall include the applicable values from the following
categories:

- Control-board state, runtime, fault flags, indicator state, and all physical interlock inputs
- The state-dependent mask identifying which interlock inputs are currently required
- Internal and backup timer states and values
- Applicator, button, coolant, magnetometer, coil, ion-pump, and temperature values
- HVPS runtime, I/O and status flags, setpoints, feedback values, and power limits
<<<

[REQUIREMENT]
UID: RQ-H1FWMC-84
TYPE: Functional
TITLE: PC Ethernet commands - Command Response
STATEMENT: >>>
The firmware shall be able to respond to commands received from a PC over Ethernet.
<<<

[REQUIREMENT]
UID: RQ-H1FWMC-85
TYPE: Functional
TITLE: Operation 11: Termination - Discharge and Return to Cold
STATEMENT: >>>
After a scalar emission completes or is stopped by the PC, the firmware shall terminate
emission, discharge, and return to Cold. A stopped emission shall retain its remaining
duration for explicit reconfirmation and release before resuming.
<<<

[REQUIREMENT]
UID: RQ-H1FWMC-86
TYPE: Functional
TITLE: Operation 12: Discharge - Ready-State Timeout
STATEMENT: >>>
The firmware shall return the system into a cold state if the system has been idle in the
ready state for a period of 2 minutes.
<<<

[REQUIREMENT]
UID: RQ-H1FWMC-87
TYPE: Functional
TITLE: Operation 12: Discharge - Staged-State Timeout
STATEMENT: >>>
The firmware shall return the system into a cold state if the system has been idle in staged
state for a period of 5 minutes.
<<<

[REQUIREMENT]
UID: RQ-H1FWMC-305
TYPE: Functional
TITLE: QC Processing
STATEMENT: >>>
The Main Control App FW shall be able to accept QC Diode values from the Head Interface
FW and process them for output to the PC Application. A QC ping command should also be
processed when received from the PC application.
<<<

[REQUIREMENT]
UID: RQ-H1FWMC-306
TYPE: Functional
TITLE: Report device information to PC
STATEMENT: >>>
The firmware shall periodically report its device information to the PC and respond to a
device-information request. The reported information shall identify the main-control and
HVPS-interface firmware releases and operating modes.
<<<

[REQUIREMENT]
UID: RQ-H1FWMC-307
TYPE: Safety
TITLE: Emission magnetometer monitoring
STATEMENT: >>>
After setting the coils and before enabling emission, the firmware shall average three
valid post-coil readings from each magnetometer axis. Emission shall not start if the
readings are unavailable. During emission, the firmware shall report a magnetometer fault
if any axis deviates from its baseline by more than 10%, with a minimum threshold of 1.0 uT,
for three consecutive packets, or if any reading is non-finite. A magnetometer fault shall
request a transition to the fault state.
<<<

[[/SECTION]]

[[/SECTION]]

[[SECTION]]
TITLE: Overview

[TEXT]
STATEMENT: >>>
The main control application firmware serves as the main logical control for system operation.

The main control application firmware monitors all the inputs from the various connections on the board
hardware. It can also be used to set and control many of the components that the main control board
interfaces with. For off the shelf components, the main control application can set/enable the motor controller drivers for cooling system pump and fans, and
can enable the ion pump controller.

The main control application firmware runs on the main control MCU of the main control board.
<<<

[[/SECTION]]

[[SECTION]]
TITLE: References

[TEXT]
STATEMENT: >>>
+--------------------------------+-------------------------------------------+
| Document ID / Reference Number | Document Title                            |
+================================+===========================================+
| DHF-GBSK-0001, Rev.1           | GBSK Software Development Plan (SDP)      |
+--------------------------------+-------------------------------------------+
| DHF-GBSK-0003, Rev.1           | GBSK Software Verification Plan (SVP)     |
+--------------------------------+-------------------------------------------+
<<<

[[/SECTION]]

[DOCUMENT]
TITLE: GBSK Main Control Bootloader FW Verification Testing Protocol
UID: DHF-GBSK-0083
METADATA:
  COMPONENT: main-control/bootloader

[GRAMMAR]
IMPORT_FROM_FILE: @grammar

[[SECTION]]
TITLE: Purpose

[TEXT]
STATEMENT: >>>
This document provides the full test protocol (a full collection of test cases) for the Main Control Bootloader 
Firmware for the GBSK 1.0 system.
<<<

[[/SECTION]]

[[SECTION]]
TITLE: Scope

[TEXT]
STATEMENT: >>>
This report contains a detailed test description to conduct verification testing of GBSK 1.0 Main Control Bootloader 
Firmware that covers GBSK Main Control Bootloader FW SRS.
<<<

[[/SECTION]]

[[SECTION]]
TITLE: Abbreviations and Definitions

[TEXT]
STATEMENT: >>>
FW
  Firmware

HVPS
  High Voltage Power Supply

SDP
  Software Development Plan

SVP
  Software Verification Plan

SW
  Software
<<<

[[/SECTION]]

[[SECTION]]
TITLE: References

[TEXT]
STATEMENT: >>>
DHF-GBSK-0001, Rev. 1: GBSK SDP

DHF-GBSK-0003, Rev. 1: GBSK SVP

[LINK: DHF-GBSK-0015]

DHF-GBSK-0031, Rev. 1: GBSK Firmware Architecture Description
<<<

[[/SECTION]]

[[SECTION]]
TITLE: Prerequisites

[TEXT]
STATEMENT: >>>
**Pre-Execution Approval**

A Pre-Execution meeting shall take place, and approved by the project manager and QA/RA.

**Objective(s)**

Verify that:

* All software, firmware, hardware, and test equipment version configurations are identified and listed in the test report prior to execution.
* Test personnel is assigned and available.

**Assumptions & Constraints**

The mcumgr examples below use the `main-control-ftdi` connection profile. Configure it once,
replacing `COM12` with the FTDI adapter's actual port:

.. code-block:: powershell

   mcumgr conn add main-control-ftdi type="serial" connstring="dev=COM12,baud=115200,mtu=124"

Use the same port in the direct serial commands below. Close any other tool using the port
before running a command. When a step calls for entering serial recovery from the running
application, use the PowerShell sequence in TC-H1FWMCBOOT-10, step 1.

**Acceptance Criteria**

All objectives met; test execution can start.
<<<

[[/SECTION]]

[[SECTION]]
PREFIX: TC-H1FWMCBOOT-
TITLE: Test Protocol

[TEST_CASE]
UID: TC-H1FWMCBOOT-6
TITLE: Invalid Image Rejection - Test Case
STATEMENT: >>>
The bootloader shall reject an invalid or unsigned update and continue to boot the existing valid application.
<<<
PREREQUISITES: >>>
1. The system is ready to start.
2. A valid signed application is installed in slot 0.
3. An invalid or unsigned `.mcumgr.bin` image is available.
<<<
STEPS: >>>
1. Enter serial recovery and record the image list before uploading:

   .. code-block:: powershell

      mcumgr -c main-control-ftdi image list

2. Upload the invalid or unsigned image to slot 1:

   .. code-block:: powershell

      mcumgr -c main-control-ftdi image upload --image 2 ".\invalid-or-unsigned.mcumgr.bin"

3. Request the image list after uploading:

   .. code-block:: powershell

      mcumgr -c main-control-ftdi image list

4. Reset the system:

   .. code-block:: powershell

      mcumgr -c main-control-ftdi reset
<<<
EXPECTED_BEHAVIOR: >>>
1. The image-list request succeeds, and the existing slot-0 image's version and hash are recorded.
2. The invalid image is not accepted for upgrade.
3. Image list does not show the uploaded image as a valid image in slot 1. The slot-0 version
   and hash match the values recorded before uploading.
4. After reset, the system boots the existing application in slot 0.
<<<
RELATIONS:
- TYPE: Parent
  VALUE: RQ-H1FWMCBOOT-1
  ROLE: Verifies

[TEST_CASE]
UID: TC-H1FWMCBOOT-8
TITLE: Secondary Image Upload - Test Case
STATEMENT: >>>
The main control bootloader firmware shall upload a signed MCUboot image to the secondary image slot.
<<<
PREREQUISITES: >>>
1. The system is ready to start.
2. A valid signed `.mcumgr.bin` image is available.
3. A valid signed application is installed in slot 0
<<<
STEPS: >>>
1. Enter serial recovery. Attempt each of the following uploads, recording the image list
   before and after each attempt:

   .. code-block:: powershell

      mcumgr -c main-control-ftdi image list
      mcumgr -c main-control-ftdi image upload ".\valid-signed.mcumgr.bin"
      mcumgr -c main-control-ftdi image list

      mcumgr -c main-control-ftdi image upload --image 0 ".\valid-signed.mcumgr.bin"
      mcumgr -c main-control-ftdi image list

      mcumgr -c main-control-ftdi image upload --image 1 ".\valid-signed.mcumgr.bin"
      mcumgr -c main-control-ftdi image list

   Verify each attempt returns an error and the reported image entries, versions, and hashes
   remain unchanged.
2. Record the image list, then upload the signed image using mcumgr direct image target 2:

   .. code-block:: powershell

      mcumgr -c main-control-ftdi image list
      mcumgr -c main-control-ftdi image upload --image 2 ".\valid-signed.mcumgr.bin"

3. Record the image list after the upload:

   .. code-block:: powershell

      mcumgr -c main-control-ftdi image list
<<<
EXPECTED_BEHAVIOR: >>>
1. Uploads without an image selector or with `--image 0` or `--image 1` are rejected. The image
   entries, versions, and hashes reported before and after each rejected attempt match.
2. Upload with `--image 2` succeeds and stores the image in slot 1.
3. Image list shows the image in slot 1 with `bootable: true` and a hash.
4. The reported slot-0 image version and hash remain unchanged after all upload attempts.
<<<
RELATIONS:
- TYPE: Parent
  VALUE: RQ-H1FWMCBOOT-3
  ROLE: Verifies

[TEST_CASE]
UID: TC-H1FWMCBOOT-9
TITLE: Interrupted Image Upload Recovery - Test Case
STATEMENT: >>>
If an image upload is interrupted, the bootloader shall ignore the incomplete image and boot the existing valid application after reset.
<<<
PREREQUISITES: >>>
1. The system is ready to start.
2. A valid signed `.mcumgr.bin` image is available.
3. A valid signed application is installed in slot 0.
<<<
STEPS: >>>
1. If the board is already in serial recovery mode, proceed to step 2. Otherwise, send
   ``*BOOTL`` followed by a newline to the running application at 115200 baud:

   .. code-block:: powershell

      $port = [System.IO.Ports.SerialPort]::new("COM12", 115200)
      try {
          $port.Open()
          $port.Write("*BOOTL`n")
      } finally {
          $port.Close()
          $port.Dispose()
      }

2. Start a secondary-slot image upload and press Ctrl+C before it completes:

   .. code-block:: powershell

      mcumgr -c main-control-ftdi image upload --image 2 ".\valid-signed.mcumgr.bin"

3. Reset the system:

   .. code-block:: powershell

      mcumgr -c main-control-ftdi reset
<<<
EXPECTED_BEHAVIOR: >>>
1. The incomplete secondary image is not selected.
2. The primary application remains bootable.
3. The system starts the primary application after reset.
<<<
RELATIONS:
- TYPE: Parent
  VALUE: RQ-H1FWMCBOOT-4
  ROLE: Verifies

[TEST_CASE]
UID: TC-H1FWMCBOOT-10
TITLE: PC Communication - Test Case
STATEMENT: >>>
The main control bootloader firmware shall respond to an mcumgr echo command while serial recovery is active.
<<<
PREREQUISITES: >>>
1. The system is ready to start.
2. A valid signed primary image is present.
<<<
STEPS: >>>
1. Send `*BOOTL\n` to the running application at 115200 baud.

   .. code-block:: powershell

      $port = [System.IO.Ports.SerialPort]::new("COM12", 115200)
      try {
          $port.Open()
          $port.Write("*BOOTL`n")
      } finally {
          $port.Close()
          $port.Dispose()
      }

2. Verify the mcumgr connection at 115200 baud:

   .. code-block:: powershell

      mcumgr -c main-control-ftdi echo ping

3. While in serial recovery mode, reset the processor using the command below:

   .. code-block:: powershell

      mcumgr -c main-control-ftdi reset
<<<
EXPECTED_BEHAVIOR: >>>
1. The application requests serial recovery and resets.
2. The bootloader replies with `ping`.
3. The next reset boots the primary application normally.
<<<
RELATIONS:
- TYPE: Parent
  VALUE: RQ-H1FWMCBOOT-5
  ROLE: Verifies

[TEST_CASE]
UID: TC-H1FWMCBOOT-11
TITLE: Recovery Entry - Test Case
STATEMENT: >>>
The main control bootloader firmware shall consume a one-shot request from the main application,
enter serial recovery for that boot only, and clear the request before the next processor reset.
<<<
PREREQUISITES: >>>
1. The system is running a valid primary application that responds to `*BOOTL\n`.
2. A PC is connected to the application and bootloader FTDI UART at 115200 baud.
<<<
STEPS: >>>
1. Send `*BOOTL\n` to the running application and observe the processor reset.

   .. code-block:: powershell

      $port = [System.IO.Ports.SerialPort]::new("COM12", 115200)
      try {
          $port.Open()
          $port.Write("*BOOTL`n")
      } finally {
          $port.Close()
          $port.Dispose()
      }

2. Connect mcumgr at 115200 baud and send an echo command:

   .. code-block:: powershell

      mcumgr -c main-control-ftdi echo recovery

3. While in serial recovery mode, reset the processor using the command below:

   .. code-block:: powershell

      mcumgr -c main-control-ftdi reset

4. Verify the primary application starts, then reset the processor once more without issuing a
   bootloader request.
<<<
EXPECTED_BEHAVIOR: >>>
1. The running application accepts the bootloader-entry command and resets the processor.
   The board enters serial recovery mode for this boot.
2. The mcumgr echo command succeeds at 115200 baud and displays ``recovery``, confirming that
   serial recovery is active.
3. The mcumgr reset command succeeds. The valid primary application in slot 0 starts normally
   instead of remaining in the requested serial recovery mode.
4. After the additional processor reset without a new bootloader-entry request, the same primary
   application starts normally again. The original request does not cause another recovery boot,
   demonstrating that it is used only once.
<<<
RELATIONS:
- TYPE: Parent
  VALUE: RQ-H1FWMCBOOT-6
  ROLE: Verifies

[TEST_CASE]
UID: TC-H1FWMCBOOT-12
TITLE: Image Validation - Test Case
STATEMENT: >>>
The main control bootloader firmware shall reject uploaded images with either a corrupted SHA-256
hash or an ECDSA P-256 signature that does not match the public key embedded in the bootloader.
<<<
PREREQUISITES: >>>
1. The system is ready to start with a valid signed primary image.
2. A copy of a signed `.mcumgr.bin` image has been modified after signing so that its SHA-256
   validation fails.
3. A second `.mcumgr.bin` image has a valid SHA-256 hash but is signed with a different ECDSA P-256
   private key from the one corresponding to the bootloader's embedded public key.
<<<
STEPS: >>>
1. Enter serial recovery and record the image list. Upload the post-signing-modified image using
   mcumgr direct image target 2, then record the image list again:

   .. code-block:: powershell

      mcumgr -c main-control-ftdi image list
      mcumgr -c main-control-ftdi image upload --image 2 ".\modified-after-signing.mcumgr.bin"
      mcumgr -c main-control-ftdi image list

2. Reset the processor and verify that the valid primary application starts:

   .. code-block:: powershell

      mcumgr -c main-control-ftdi reset

3. Re-enter serial recovery and record the image list. Upload the image signed with the
   non-matching key using direct image target 2, then record the image list again:

   .. code-block:: powershell

      mcumgr -c main-control-ftdi image list
      mcumgr -c main-control-ftdi image upload --image 2 ".\wrong-key.mcumgr.bin"
      mcumgr -c main-control-ftdi image list

4. If mcumgr reports a hash, attempt to confirm the uploaded image, then reset the processor:

   .. code-block:: powershell

      $slot1Hash = Read-Host "Enter the slot-1 image hash reported by mcumgr"
      mcumgr -c main-control-ftdi image confirm $slot1Hash
      mcumgr -c main-control-ftdi reset
<<<
EXPECTED_BEHAVIOR: >>>
1. The post-signing-modified image is not reported as a bootable slot-1 image and cannot be selected
   for upgrade. The slot-0 version and hash match the values recorded before uploading.
2. The valid primary application remains selected and starts after reset.
3. The image signed with the non-matching key is not reported as a bootable slot-1 image and cannot
   be confirmed for upgrade. The slot-0 version and hash match the values recorded before uploading.
4. The valid primary application remains selected and starts after the final reset.
<<<
RELATIONS:
- TYPE: Parent
  VALUE: RQ-H1FWMCBOOT-7
  ROLE: Verifies

[TEST_CASE]
UID: TC-H1FWMCBOOT-13
TITLE: Image Upgrade - Test Case
STATEMENT: >>>
Verify that the main control bootloader permanently upgrades to a confirmed, validated secondary
image and exchanges the images in the primary and secondary slots.
<<<
PREREQUISITES: >>>
1. The system is running a valid signed primary image in slot 0 with an identifiable version and hash.
2. A valid signed `.mcumgr.bin` image with a different identifiable version and hash is available.
3. Use the following command when a step requires entering serial recovery from the running
   application. Replace COM12 with the port configured for main-control-ftdi:

   .. code-block:: powershell

      $port = [System.IO.Ports.SerialPort]::new("COM12", 115200)
      try {
          $port.Open()
          $port.Write("*BOOTL`n")
      } finally {
          $port.Close()
          $port.Dispose()
      }
<<<
STEPS: >>>
1. Enter serial recovery using the command in prerequisite 3, then record the slot-0 image hash:

   .. code-block:: powershell

      mcumgr -c main-control-ftdi image list

2. Upload the new image to slot 1 (the secondary slot) using mcumgr direct image target 2:

   .. code-block:: powershell

      mcumgr -c main-control-ftdi image upload --image 2 ".\new-version.mcumgr.bin"

3. Request image list and record the new slot-1 image hash:

   .. code-block:: powershell

      mcumgr -c main-control-ftdi image list

4. Confirm the new image using its recorded hash:

   .. code-block:: powershell

      $slot1Hash = Read-Host "Enter the slot-1 image hash reported by mcumgr"
      mcumgr -c main-control-ftdi image confirm $slot1Hash

5. Reset the processor to apply the upgrade:

   .. code-block:: powershell

      mcumgr -c main-control-ftdi reset

6. Verify that the new application version starts.
7. Enter serial recovery, then request the image list:

   .. code-block:: powershell

      mcumgr -c main-control-ftdi image list

8. Reset the processor without confirming another image and verify that the new application version
   starts again:

   .. code-block:: powershell

      mcumgr -c main-control-ftdi reset
<<<
EXPECTED_BEHAVIOR: >>>
1. The board enters serial recovery, and the image list reports the existing primary image in
   slot 0 with its version and hash. The original slot-0 hash is recorded.
2. The upload completes successfully and stores the new image in slot 1 (the secondary slot).
3. The image list reports the new image in slot 1 as bootable, with the expected version and hash.
   The new slot-1 hash is recorded, and the original image remains in slot 0 with its original hash.
4. The image-confirm command succeeds for the recorded slot-1 hash.
5. The reset command succeeds, and the bootloader applies the confirmed upgrade.
6. The new application starts normally and reports the expected new version.
7. The board re-enters serial recovery. The image list reports the new image in slot 0 with the
   hash recorded in step 3, and the original image in slot 1 with the hash recorded in step 1.
8. After another reset without confirming another image, the new application starts again and
   reports the expected new version. The system does not revert to the original application.
<<<
RELATIONS:
- TYPE: Parent
  VALUE: RQ-H1FWMCBOOT-8
  ROLE: Verifies

[[/SECTION]]

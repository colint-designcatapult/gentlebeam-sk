[DOCUMENT]
TITLE: GBSK Main Control Bootloader FW Software Requirements Specification
UID: DHF-GBSK-0015
METADATA:
  COMPONENT: main-control/bootloader

[GRAMMAR]
IMPORT_FROM_FILE: @grammar

[[SECTION]]
TITLE: Purpose

[TEXT]
STATEMENT: >>>
The purpose of this document is to provide Software Requirements Specifications for the GBSK Main
Control Bootloader Firmware (FW).
<<<

[[/SECTION]]

[[SECTION]]
TITLE: Scope

[TEXT]
STATEMENT: >>>
This document describes all requirements of the GBSK Main Control Bootloader FW.
The information in this document has been derived from the VoxelRay GBSK Product Requirements
Specification, as referenced in this document.

\*The term Software applies to both Software and Firmware systems.
<<<

[[/SECTION]]

[[SECTION]]
TITLE: Abbreviations and Definitions

[TEXT]
STATEMENT: >>>
FW
  Firmware

MCU
  Microcontroller Unit

PRS
  Product Requirements Specification

SDP
  Software Development Plan

SRS
  Software Requirements Specification

SW
  Software
<<<

[[/SECTION]]

[[SECTION]]
TITLE: Overview

[TEXT]
STATEMENT: >>>
The Main Control Bootloader firmware allows the system to update the main control application
firmware.

The Main Board Bootloader firmware runs on the main control MCU of the main control board.
<<<

[[/SECTION]]

[[SECTION]]
TITLE: References

[TEXT]
STATEMENT: >>>

DHF-GBSK-0001, Rev. 1: GBSK Software Development Plan (SDP)

DHF-GBSK-0002: VoxelRay Product Requirements Specification (PRS)
<<<

[[/SECTION]]

[[SECTION]]
PREFIX: RQ-H1FWMCBOOT-
TITLE: Requirements

[REQUIREMENT]
UID: RQ-H1FWMCBOOT-1
TYPE: Functional
TITLE: Application Image Validation
STATEMENT: >>>
The main control bootloader firmware shall jump to execution of the main application if and only
if the primary-slot MCUboot image has a valid header, SHA-256 image hash, and ECDSA P-256
signature that matches the public key embedded in the bootloader.
<<<

[REQUIREMENT]
UID: RQ-H1FWMCBOOT-3
TYPE: Functional
TITLE: Secondary-Only Image Upload
STATEMENT: >>>
The main control bootloader firmware shall allow mcumgr image uploads only to the secondary image
slot and reject uploads targeting the primary image slot.
<<<

[REQUIREMENT]
UID: RQ-H1FWMCBOOT-4
TYPE: Functional
TITLE: Interrupted Image Upload Recovery
STATEMENT: >>>
If an image upload is interrupted, the main control bootloader firmware shall not select the
incomplete image for execution and shall boot the existing valid application after reset.
<<<

[REQUIREMENT]
UID: RQ-H1FWMCBOOT-5
TYPE: Functional
TITLE: PC communication
STATEMENT: >>>
The main control bootloader firmware shall respond to an mcumgr echo command while serial recovery
is active.
<<<

[REQUIREMENT]
UID: RQ-H1FWMCBOOT-6
TYPE: Functional
TITLE: Recovery entry
STATEMENT: >>>
The main control bootloader firmware shall enter serial recovery when it observes and clears the
one-shot bootloader request written by the main application before processor reset.
<<<

[REQUIREMENT]
UID: RQ-H1FWMCBOOT-7
TYPE: Functional
TITLE: Image validation
STATEMENT: >>>
The main control bootloader firmware shall reject an uploaded image that does not contain a valid
SHA-256 hash and ECDSA P-256 signature matching its embedded public key.
<<<

[REQUIREMENT]
UID: RQ-H1FWMCBOOT-8
TYPE: Functional
TITLE: Image upgrade
STATEMENT: >>>
The main control bootloader firmware shall permanently upgrade to a validated secondary-slot image
after the image is confirmed and the processor is reset, using the scratch flash area to swap the
primary and secondary slots.
<<<

[[/SECTION]]

[DOCUMENT]
TITLE: GBSK Main Control Bootloader FW Software Design Document
UID: DHF-GBSK-0078
METADATA:
  COMPONENT: main-control/bootloader

[GRAMMAR]
IMPORT_FROM_FILE: @grammar

[[SECTION]]
TITLE: Purpose

[TEXT]
STATEMENT: >>>
The purpose of this document is to outline the design specifications of the GBSK Main Control
Bootloader Firmware.
<<<

[[/SECTION]]

[[SECTION]]
TITLE: Scope

[TEXT]
STATEMENT: >>>
This document describes the design modules and sub-modules of the GBSK Main Control Bootloader
Firmware.

The information in this document is derived from the Main Control Bootloader FW SRS, referenced in this
document.

\*The term Software applies to both Software and Firmware components.
<<<

[[/SECTION]]

[[SECTION]]
TITLE: Abbreviations and Definitions

[TEXT]
STATEMENT: >>>
FW
  Firmware

MCU
  Microcontroller Unit

PRS
  Product Requirements Specification

SDP
  Software Development Plan

SRS
  Software Requirements Specification

SW
  Software
<<<

[[/SECTION]]

[[SECTION]]
TITLE: Overview

[TEXT]
STATEMENT: >>>
The Main Control Bootloader firmware allows the system to update the main control application firmware.

The Main Control Bootloader firmware runs on the main control MCU of the main control board.
<<<

[[/SECTION]]

[[SECTION]]
TITLE: References

[TEXT]
STATEMENT: >>>
DHF-GBSK-0001, Rev. 1: GBSK Software Development Plan (SDP)

DHF-GBSK-0003, Rev. 1: GBSK Software Verification Plan (SVP)

[LINK: DHF-GBSK-0015]

DHF-GBSK-0031, Rev. 1: GBSK Firmware Architecture Description
<<<

[[/SECTION]]

[[SECTION]]
TITLE: Architecture Overview

[[SECTION]]
TITLE: High Level System Architecture

[TEXT]
STATEMENT: >>>
.. raw:: html

    <pre class="mermaid">
    flowchart LR

    PC["Main Control Bootloader<br/>PC Application"]

    subgraph BL["Main Control Bootloader<br/>Firmware"]
        USB["USB"]
    end

    FLASH[(Main Control Flash Memory)]

    PC --> USB
    BL --> FLASH
    </pre>
<<<

[[/SECTION]]

[[SECTION]]
TITLE: Main Modules

[TEXT]
STATEMENT: >>>
**Main Control Bootloader Firmware** – The firmware is stored at the base memory address on the
microcontroller and uses MCUboot to validate, select, and swap signed application images.

**Main Control Bootloader PC Application** – This app uses mcumgr serial recovery to upload a signed
MCUboot image to the secondary slot, verify its presence, confirm it, and reset the controller.

**Flash Memory** – Contains a 200 KiB bootloader region, 800 KiB primary and secondary image slots,
and a 64 KiB scratch area used by the swap algorithm.
<<<

[[/SECTION]]

[[SECTION]]
PREFIX: SW-H1FWMCBOOT-
TITLE: Design Items

[DESIGN_ITEM]
UID: SW-H1FWMCBOOT-11
TITLE: PC Communication Interface
STATEMENT: >>>
The firmware communicates with the PC via the microcontroller’s serial UART interface. The
firmware both receives and transmits data on this UART port. Due to the nature of UART having
independent transmit and receive lines, the transmit and receive functionality operate
independently. As the UART baud rate is relatively slow compared to the processing speed of the
microcontroller, both sending and receiving data is performed with non-blocking interrupt callback
functions.

Transmitted data is sent as a buffer of bytes, representing a singular data packet to the PC, with
the interrupt callback occurring once all data bytes have been transmitted. The firmware sets a flag
when transmission is initiated, and clears the flag after transmission is finished, to not create
transmission conflicts on the transmit line.

Reception is performed one byte at a time, with the interrupt callback occurring once a data byte is
available. The parsing of the received byte is done to determine whether a complete data packet
has been received from the PC, as according to the communication protocol. Once a completed
data packet has been received, the firmware sets a flag for further data processing outside of the
parsing inside of the interrupt callback.
<<<
RELATIONS:
- TYPE: Parent
  VALUE: RQ-H1FWMCBOOT-3
  ROLE: Refines

[DESIGN_ITEM]
UID: SW-H1FWMCBOOT-12
TITLE: PC Communication Processing
STATEMENT: >>>
The bootloader exposes the MCUboot mcumgr serial-recovery service over the FTDI UART at 115200
baud, 8-N-1, with an MTU of 124 bytes. mcumgr packets are framed and base64-encoded by the
serial-recovery implementation. The enabled commands are echo, image list, image upload, image
confirm, and reset.

The host directs an update to mcumgr image target 2, which is mapped by the platform flash map to
the secondary slot. The host obtains the secondary image hash from image list before requesting
image confirm. The bootloader responds using mcumgr protocol frames and does not emit diagnostic
text on this UART while serial recovery is active.
<<<
RELATIONS:
- TYPE: Parent
  VALUE: RQ-H1FWMCBOOT-1
  ROLE: Refines
- TYPE: Parent
  VALUE: RQ-H1FWMCBOOT-5
  ROLE: Refines

[DESIGN_ITEM]
UID: SW-H1FWMCBOOT-13
TITLE: Application Program Handling
STATEMENT: >>>
At startup, the bootloader checks the general-purpose backup register for the one-shot bootloader
request written by the main application in response to `*BOOTL\n`. When present, the bootloader
clears the request and enters serial recovery. Otherwise it calls MCUboot boot_go() to validate the
primary image and process a confirmed secondary-image upgrade.

The application image contains a 512-byte MCUboot header and SHA-256, key-hash, and ECDSA P-256
signature TLVs. MCUboot validates these values against the public key compiled into the bootloader.
If no valid primary image is available, serial recovery remains active instead of jumping to the
application.
<<<
RELATIONS:
- TYPE: Parent
  VALUE: RQ-H1FWMCBOOT-1
  ROLE: Refines

[DESIGN_ITEM]
UID: SW-H1FWMCBOOT-14
TITLE: Manufacturer Hardware Abstraction
STATEMENT: >>>
The firmware integrates source code provided by the manufacturer of the microcontroller unit to
interface with various peripherals of the microcontroller. These include functions to interface with
the following peripherals of the microcontroller:

-UART serial port

-GPIO

-Flash memory controller
<<<
RELATIONS:
- TYPE: Parent
  VALUE: RQ-H1FWMCBOOT-1
  ROLE: Refines
- TYPE: Parent
  VALUE: RQ-H1FWMCBOOT-3
  ROLE: Refines
- TYPE: Parent
  VALUE: RQ-H1FWMCBOOT-4
  ROLE: Refines
- TYPE: Parent
  VALUE: RQ-H1FWMCBOOT-5
  ROLE: Refines

[DESIGN_ITEM]
UID: SW-H1FWMCBOOT-15
TITLE: Flash Memory Processing
STATEMENT: >>>
The platform flash map exposes an 800 KiB primary image slot at `0x00432000`, an 800 KiB secondary
image slot at `0x004FA000`, and a 64 KiB scratch area at `0x005C2000`. The flash backend reports
8 KiB erase sectors to MCUboot and performs page-aligned 512-byte read-modify-write operations for
arbitrary flash-area writes.

During upload, MCUboot progressively erases only secondary-slot sectors required by incoming data.
During a confirmed upgrade, MCUboot exchanges the primary and secondary images using the scratch
area. The bootloader flash region is not exposed through the mcumgr image-upload mapping.
<<<
RELATIONS:
- TYPE: Parent
  VALUE: RQ-H1FWMCBOOT-3
  ROLE: Refines
- TYPE: Parent
  VALUE: RQ-H1FWMCBOOT-4
  ROLE: Refines

[DESIGN_ITEM]
UID: SW-H1FWMCBOOT-16
TITLE: Image Authentication and Upgrade
STATEMENT: >>>
The bootloader embeds an ECDSA P-256 public key and uses TinyCrypt to verify image signatures.
The build process signs application images with the matching private key. The image list service
reports only images that pass MCUboot validation; therefore a completed upload is not accepted as
a successful update until the secondary image appears with a hash and is confirmed.
<<<
RELATIONS:
- TYPE: Parent
  VALUE: RQ-H1FWMCBOOT-7
  ROLE: Refines
- TYPE: Parent
  VALUE: RQ-H1FWMCBOOT-8
  ROLE: Refines

[DESIGN_ITEM]
UID: SW-H1FWMCBOOT-17
TITLE: Recovery Request
STATEMENT: >>>
The main application writes a magic value to general-purpose backup register zero before a software
reset in response to `*BOOTL\n`. The bootloader compares this value during startup, clears it before
entering serial recovery, and otherwise proceeds with normal image validation. This prevents stray
UART data from entering serial recovery indefinitely.
<<<
RELATIONS:
- TYPE: Parent
  VALUE: RQ-H1FWMCBOOT-6
  ROLE: Refines

[[/SECTION]]

[[/SECTION]]

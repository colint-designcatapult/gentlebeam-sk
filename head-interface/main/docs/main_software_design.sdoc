[DOCUMENT]
TITLE: GBSK Head Interface FW Software Design Document
UID: DHF-GBSK-0114
METADATA:
  COMPONENT: head-interface/main

[GRAMMAR]
IMPORT_FROM_FILE: @grammar

[[SECTION]]
TITLE: Purpose

[TEXT]
STATEMENT: >>>
The purpose of this document is to outline the design specifications of the GBSK Head Interface
Firmware.
<<<

[[/SECTION]]

[[SECTION]]
TITLE: Scope

[TEXT]
STATEMENT: >>>
This document describes the design modules and sub-modules of the GBSK Head Interface Firmware.
The information in this document is derived from the Head Interface FW SRS, referenced in this
document.

*The term Software applies to both Software and Firmware components.*
<<<

[[/SECTION]]

[[SECTION]]
TITLE: Abbreviations and Definitions

[TEXT]
STATEMENT: >>>
FW
  Firmware

MCU
  Microcontroller Unit

PRS
  Product Requirements Specification

SDP
  Software Development Plan

SRS
  Software Requirements Specification

SW
  Software
<<<

[[/SECTION]]

[[SECTION]]
TITLE: Overview

[TEXT]
STATEMENT: >>>
The head interface firmware is used to read various input data from peripherals such as cooling system
sensors, magnetometers, and collimator identification. This firmware sends feedback information to the
main control application firmware. The head interface firmware can also set various patterns to the head
base LED ring for visual indication. The pattern is based off commands received from the main control
application firmware. The head interface firmware cycles the illumination LED mode in response to
the illumination membrane-button input.
<<<

[[/SECTION]]

[[SECTION]]
TITLE: References

[TEXT]
STATEMENT: >>>
DHF-GBSK-0001, Rev. 1: GBSK Software Development Plan (SDP)

DHF-GBSK-0003, Rev. 1: GBSK Software Verification Plan (SVP)

DHF-GBSK-0023, Rev. 1: GBSK Head Interface Software Requirements Specification (SRS)

DHF-GBSK-0031, Rev. 1: GBSK Firmware Architecture Description
<<<

[[/SECTION]]

[[SECTION]]
TITLE: Architecture Overview

[[SECTION]]
TITLE: High Level System Architecture

[TEXT]
STATEMENT: >>>
.. raw:: html

   <pre class="mermaid">
   flowchart TB

    FW["Main Control<br/>Firmware"]
    EEPROM["EEPROM"]

    subgraph HI["Head Interface"]

        GPIO["GPIO"]
        PROC["Processing"]
        ADC["ADC"]
        SPI["SPI"]
        UART["UART"]
        I2C["I2C"]

        GPIO --- PROC
        PROC --- ADC

        SPI --- PROC
        UART --- PROC
        I2C --- PROC
    end

    SPI <--> EEPROM
    UART <--> FW

    Lasers <-- GPIO
    Interlocks --> GPIO
    Buttons --> GPIO

    Magnetometers --> I2C
    SPI --> IndicatorLEDs["Indicator LED Ring"]

    ADC <--> Temp["Temperature<br/>Sensor"]
    ADC <--> Pressure["Pressure<br/>Sensor"]
    ADC <--> Flow["Flow<br/>Sensor"]
   </pre>
<<<

[[/SECTION]]

[[SECTION]]
TITLE: Main Modules

[TEXT]
STATEMENT: >>>
Processing Loop - The main loop processes analog and digital signals and uses them to report Head
subsystem data back to the Main Control Firmware. Requests from the main control firmware are also
handled and responded to such as changing the output state of the LED Ring.

Buttons - The Head Interface reads 5 GPIO buttons that can change the function for the user.

Indicator LED Ring - 51 DotStar RGB LEDs controlled through SPI. Commands received from the main
control firmware select a non-blocking color effect that is advanced by the processing loop.

Analog Sensors - The Head Interface reads analog signal data from Water Temperature, Pressure, and
Flow sensors. This analog data is processed and then reported to the Main Control firmware. Sensors
can determine limits that may trigger a fault condition.

Digital Sensors - The Head Interface reads digital data from Magnetometer IC's mounted near the
deflecting coils. This data is processed and then reported to the Main Control firmware. These sensors
can create responses such as coil level adjustments or possibly fault conditions.

EEPROM - Nonvolatile data storage.
<<<

[[/SECTION]]

[[SECTION]]
PREFIX: SW-H1FHI-
TITLE: Design Items

[DESIGN_ITEM]
UID: SW-H1FHI-26
TITLE: Manufacturer Hardware Abstraction
STATEMENT: >>>
The firmware integrates source code provided by the manufacturer of the microcontroller unit to
interface with various peripherals of the microcontroller. These include functions to interface with
the following peripherals of the microcontroller:

- UART serial port

- I2C serial port

- ADC peripheral

- Pulse width modulation (PWM)

- GPIO
<<<
RELATIONS:
- TYPE: Parent
  VALUE: RQ-H1FHI-1
  ROLE: Refines
- TYPE: Parent
  VALUE: RQ-H1FHI-2
  ROLE: Refines
- TYPE: Parent
  VALUE: RQ-H1FHI-6
  ROLE: Refines
- TYPE: Parent
  VALUE: RQ-H1FHI-8
  ROLE: Refines
- TYPE: Parent
  VALUE: RQ-H1FHI-9
  ROLE: Refines
- TYPE: Parent
  VALUE: RQ-H1FHI-10
  ROLE: Refines
- TYPE: Parent
  VALUE: RQ-H1FHI-11
  ROLE: Refines
- TYPE: Parent
  VALUE: RQ-H1FHI-12
  ROLE: Refines
- TYPE: Parent
  VALUE: RQ-H1FHI-13
  ROLE: Refines
- TYPE: Parent
  VALUE: RQ-H1FHI-53
  ROLE: Refines

[DESIGN_ITEM]
UID: SW-H1FHI-27
TITLE: Input Signals
STATEMENT: >>>
The firmware has 5 inputs which represent five different physical buttons which the system user
can press. These five inputs are debounced by sampling the state of the input signals every time a
processing flag gets set. This processing flag is set every 1 msec. When an input first differs from
its stored state, the firmware starts a 30 msec debounce countdown and ignores further transitions
during the countdown. When the countdown expires, the firmware samples the input again. If it
still differs from the stored state, the firmware updates the button state for processing and
reporting to the main control application firmware.
<<<
RELATIONS:
- TYPE: Parent
  VALUE: RQ-H1FHI-11
  ROLE: Refines
- TYPE: Parent
  VALUE: RQ-H1FHI-55
  ROLE: Refines

[DESIGN_ITEM]
UID: SW-H1FHI-28
TITLE: Output Signals
STATEMENT: >>>
The firmware controls the brightness and effects of the illumination LEDs through one PWM output.
Off uses 0% duty cycle, Dim Brightness uses 10%, Normal Brightness uses 20%, and High Brightness
uses 30%. The Breathing Effect follows a smooth cycle from 0% to 30% and back to 0% over a
3-second period.
<<<
RELATIONS:
- TYPE: Parent
  VALUE: RQ-H1FHI-6
  ROLE: Refines

[DESIGN_ITEM]
UID: SW-H1FHI-29
TITLE: Magnetometers
STATEMENT: >>>
The firmware periodically reads two external magnetometers on the same I2C bus. Both
magnetometers are of the same make and model but vary in their I2C addresses. The firmware
alternates between reading each magnetometer. The X, Y, and Z values of the magnetometer are
read and subsequently sent to the main control board for the data to be sent to the PC for
treatment plan parameter compensation.
<<<
RELATIONS:
- TYPE: Parent
  VALUE: RQ-H1FHI-10
  ROLE: Refines

[DESIGN_ITEM]
UID: SW-H1FHI-30
TITLE: Flow Sensor
STATEMENT: >>>
The firmware monitors the flow sensor digital input signal once every millisecond (based on a flag
that is set inside of a time-based interrupt firing once every millisecond). The firmware checks for a
toggling state of the flow sensor input. Based on the number of signal toggles within a fixed amount
of time, the flow rate is calculated.
<<<
RELATIONS:
- TYPE: Parent
  VALUE: RQ-H1FHI-12
  ROLE: Refines

[DESIGN_ITEM]
UID: SW-H1FHI-31
TITLE: Pressure Sensor
STATEMENT: >>>
The firmware reads and converts the analog signal from the pressure sensor using the internal
ADC of the microcontroller.
<<<
RELATIONS:
- TYPE: Parent
  VALUE: RQ-H1FHI-13
  ROLE: Refines

[DESIGN_ITEM]
UID: SW-H1FHI-32
TITLE: Temperature Sensor
STATEMENT: >>>
The firmware reads a thermistor temperature sensor to determine the water temperature. The
reading is performed by the internal ADC on the microcontroller. The reading value is converted
into a temperature using a lookup table and interpolation to derive the approximate intermediate
values between lookup values. While the actual thermistor conversion is not linear, each step is
small enough where linear interpolation is good enough.
<<<
RELATIONS:
- TYPE: Parent
  VALUE: RQ-H1FHI-1
  ROLE: Refines

[DESIGN_ITEM]
UID: SW-H1FHI-33
TITLE: Control Communication Interface
STATEMENT: >>>
The firmware communicates with the main control board via the microcontroller's USART2 serial
interface. The firmware both receives and transmits data on this UART port, and its UART callbacks
ignore completion events from other UART instances. Because UART has independent transmit and
receive lines, the transmit and receive functionality operates independently. Sending and receiving
data is performed with nonblocking interrupt callback functions.

Transmitted data is sent as a buffer of bytes representing a single data packet to the main control
board. The interrupt callback occurs once all data bytes have been transmitted. The firmware sets a flag
when transmission is initiated, and clears the flag after transmission is finished, so as to not create
transmission conflicts on the transmit line.

Reception is performed one byte at a time. Each receive interrupt stores the completed byte in a
32-byte ring buffer and immediately re-arms USART2 reception for the next byte. The processing loop
drains queued bytes in order and parses them according to the communication protocol. If the ring
buffer fills before it is drained, reception continues by discarding the oldest unread byte and
recording the overflow.

As transmission on UART is asynchronous both in terms of clock as well as word alignment (within
a packet), a 'sync value' is utilized at the start of each packet to help synchronize communication
in case of any lost or missing bytes.
<<<
RELATIONS:
- TYPE: Parent
  VALUE: RQ-H1FHI-8
  ROLE: Refines

[DESIGN_ITEM]
UID: SW-H1FHI-34
TITLE: Control Communication Data
STATEMENT: >>>
In normal firmware, the data received from the main control board is a 12-byte command. Bytes
0 through 7 contain the desired indicator LED output as duplicated values and complements.
Bytes 8 through 11 contain the desired QC acquisition state using the same duplicated-value and
complement integrity check. Invalid integrity fields are ignored. Calibration firmware retains the
legacy 8-byte indicator-only command.

The normal-firmware data transmitted to the main control board includes cooling feedback, buttons,
magnetometers, and the 64-bit collimator ID in the established fields. It appends the unsigned
32-bit channel 0 and channel 1 QC accumulation sums, their independent unsigned sample counts,
and the QC acquisition state. Channel 0 contains the diode connected directly to PC2
(``ADC1_IN12``). Channel 1 remains in the packet for wire compatibility and is reported as zero
samples, zero accumulation, and disconnected. Calibration firmware retains the legacy packet
layout.
<<<
RELATIONS:
- TYPE: Parent
  VALUE: RQ-H1FHI-2
  ROLE: Refines
- TYPE: Parent
  VALUE: RQ-H1FHI-8
  ROLE: Refines

[DESIGN_ITEM]
UID: SW-H1FHI-35
TITLE: ADC Peripheral
STATEMENT: >>>
The firmware utilizes the internal ADC of the microcontroller to measure the pressure and
temperature sensors. Each signal is on a separate ADC channel. The firmware continuously
alternates between each channel to get new readings.
<<<
RELATIONS:
- TYPE: Parent
  VALUE: RQ-H1FHI-1
  ROLE: Refines
- TYPE: Parent
  VALUE: RQ-H1FHI-13
  ROLE: Refines

[DESIGN_ITEM]
UID: SW-H1FHI-36
TITLE: Buttons
STATEMENT: >>>
After monitoring for debouncing, the firmware also performs specific actions based on which
buttons were pressed. The following actions are mapped to specific button presses:

- A detected press of the LED button advances the illumination LEDs to the next mode in the
  following sequence: Dim Brightness, Normal Brightness, High Brightness, Breathing Effect, Off,
  then back to Dim Brightness.
<<<
RELATIONS:
- TYPE: Parent
  VALUE: RQ-H1FHI-6
  ROLE: Refines

[DESIGN_ITEM]
UID: SW-H1FHI-38
TITLE: Indicator LED Data
STATEMENT: >>>
The indicator ring contains 51 DotStar RGB LEDs connected to SPI1. The driver maintains one color
and brightness entry per LED and transmits a DotStar start frame, the 51 LED frames, and a latch
frame sized for the strip. Static color commands and animation frames use the same strip buffer.

The main control command supplies an LED sequence ID as a duplicated byte followed by two copies
of its one's complement. Valid commands select the following indications; sequence ID 3 is unused:

- ``LED_SEQ_OFF`` (0): all LEDs off.
- ``LED_SEQ_COLD`` (1): white pulsating over a 3-second cycle.
- ``LED_SEQ_WARMUP`` (2): a 15-LED purple segment rotating every 75 msec while pulsating over a
  3-second cycle.
- ``LED_SEQ_PRIMED`` (4): the full ring alternating between blue and green every 500 msec.
- ``LED_SEQ_SETUP`` (5): separate six-LED blue and orange segments rotating every 75 msec, with
  blue leading and orange following by 14 LED positions on an otherwise dark ring.
- ``LED_SEQ_READY`` (6): solid green.
- ``LED_SEQ_XRAY`` (7): amber pulsating over a 3-second cycle.
- ``LED_SEQ_IDLE`` (8): solid white.
- ``LED_SEQ_FAULT`` (9): red alternating with off every 250 msec.

The non-blocking effect engine is serviced every 20 msec from the processing loop. Rotation and
pulsation use independent elapsed-time accumulators when combined. Pulsation scales the 8-bit RGB
channels instead of the DotStar 5-bit global brightness, providing a finer visible fade. Selecting a
static color stops any active animation before updating the strip.
<<<
RELATIONS:
- TYPE: Parent
  VALUE: RQ-H1FHI-14
  ROLE: Refines

[DESIGN_ITEM]
UID: SW-H1FHI-39
TITLE: Quality Control (QC)
STATEMENT: >>>
One analog X-ray detector diode is connected directly to PC2 (``ADC1_IN12``) and maps to wire
channel 0. Wire channel 1 is retained for compatibility but has no detector and remains zero and
disconnected. While idle, PC2 is included in the interrupt-driven ADC1 monitoring sequence so the
instantaneous reading remains available.

An accepted Accumulating command suspends temperature and pressure monitoring, configures ADC1
for TIM2 update triggering, and starts a finite normal-mode DMA2 Stream 0 burst into 32 unsigned
halfword samples. TIM2 continues its LED-ring PWM role and produces an ADC trigger at approximately
111.1 Hz. The first 16 conversions are consumed at DMA half-transfer and the final 16 at
transfer-complete. Each half is consumed at most once before the next finite burst starts, and each
12-bit conversion is added to channel 0's unsigned 32-bit sum and sample count.

Stop is bounded at a DMA half boundary. A request before half-transfer aborts the burst without
counting it; a request after half-transfer preserves the first half and lets the second half finish
before publishing Complete. ADC or DMA errors invalidate the active transfer, preserve only
already committed halves, and publish Error. Complete and Error both restore the software-triggered
ADC1 monitoring sequence. Command transitions occur in the scheduler rather than inside UART or
DMA callbacks. A reported snapshot copies both sums, both counts, and state atomically so one
main-control packet cannot mix values from different acquisition instants.
<<<
RELATIONS:
- TYPE: Parent
  VALUE: RQ-H1FHI-53
  ROLE: Refines

[[/SECTION]]

[[/SECTION]]

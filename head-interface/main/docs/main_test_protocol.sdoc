[DOCUMENT]
TITLE: GBSK Head Interface Application FW Verification Testing Protocol
UID: DHF-GBSK-0119

[GRAMMAR]
IMPORT_FROM_FILE: @grammar

[[SECTION]]
TITLE: Purpose

[TEXT]
STATEMENT: >>>
This document provides the full test protocol (a full collection of test cases) for the Head Interface
Firmware for the GBSK 1.0 system.
<<<

[[/SECTION]]

[[SECTION]]
TITLE: Scope

[TEXT]
STATEMENT: >>>
This report contains a detailed test description to conduct verification testing of GBSK 1.0 Head
Interface Firmware that covers GBSK Head Interface FW SRS.
<<<

[[/SECTION]]

[[SECTION]]
TITLE: Abbreviations and Definitions

[TEXT]
STATEMENT: >>>
FW
  Firmware

HVPS
  High Voltage Power Supply

SDP
  Software Development Plan

SVP
  Software Verification Plan

SW
  Software
<<<

[[/SECTION]]

[[SECTION]]
TITLE: References

[TEXT]
STATEMENT: >>>
DHF-GBSK-0001, Rev. 1: GBSK SDP

DHF-GBSK-0003, Rev. 1: GBSK SVP

[LINK: DHF-GBSK-0023]

DHF-GBSK-0031, Rev. 1: GBSK Firmware Architecture Description
<<<

[[/SECTION]]

[[SECTION]]
TITLE: Prerequisites

[TEXT]
STATEMENT: >>>
**Pre-Execution Approval**

A Pre-Execution meeting shall take place, and approved by the project manager and QA/RA.

**Objective(s)**

Verify that:

* All software, firmware, hardware, and test equipment version configurations are identified and listed in the test report prior to execution.
* Test personnel is assigned and available.

**Assumptions & Constraints**

None

**Acceptance Criteria**

All objectives met; test execution can start.
<<<

[[/SECTION]]

[[SECTION]]
PREFIX: TC-H1FHI-
TITLE: Test Protocol

[TEST_CASE]
UID: TC-H1FHI-14
TITLE: Collimator Interlock - Test Case
STATEMENT: >>>
When user applies fake emissions (e.g. fake HVPS) to the system and remove Collimator verify head interface interlock fault.
<<<
PREREQUISITES: >>>
1. The system is ready to run.
2. A fake emission should be simulated for the plan (e.g. fake HVPS)
3. A 20 second treatment plan should be ready to load and run.
<<<
STEPS: >>>
1. Power on the system with modified no emission output (e.g. fake HVPS).
2. Load a 20 second treatment plan.
3. Start the emission for 5 seconds.
4. Remove the collimator.
5. Check the fault.
<<<
EXPECTED_BEHAVIOR: >>>
1. Verify the system is up and ready to run.
2. Verify the plan is loaded successfully.
3. Verify the emission is started.
4. Verify physically that the collimator is removed.
5. Verify head interface interlock fault displayed.
<<<
RELATIONS:
- TYPE: Parent
  VALUE: RQ-H1FHI-2
  ROLE: Verifies

[TEST_CASE]
UID: TC-H1FHI-15
TITLE: Indicator LEDs 1 - Test Case
STATEMENT: >>>
User can verify the color of the LED lights for different scenarios which can be listed as follows:

1. Flashing red indicating a fault.
2. Solid green indicating ready to emit.
3. Pulsating amber indicating emission.
<<<
PREREQUISITES: >>>
1. System is up and ready to run a treatment plan
2. A treatment plan is ready to run.
3. Tester should view LEDs remotely from a safe location through webcam or camera as to not be exposed to radiation.
<<<
STEPS: >>>
1. Load a treatment plan of 1 point of duration 10 seconds or more.
2. Check the status of the system.
3. Check the LED light.
4. Start the emission.
5. Check the LED light.
6. After about 5 seconds, click the e-stop button on external monitor to trigger a fault.

7. Check the LED light.
<<<
EXPECTED_BEHAVIOR: >>>
1. Verify the plan is loaded successfully.
2. Verify the state is Ready
3. Verify it’s Solid Green and ready to emit.
4. Verify the emission started.
5. Verify it is pulsating amber.
6. Verify the fault is created.
7. Verify it is blinking Red.
<<<
RELATIONS:
- TYPE: Parent
  VALUE: RQ-H1FHI-14
  ROLE: Verifies

[TEST_CASE]
UID: TC-H1FHI-16
TITLE: Cooling System Pressure - Test Case
STATEMENT: >>>
When a service user powers on the system and checks the service screen, he/she should view pressure values before and after the loading the treatment plan.
<<<
PREREQUISITES: >>>
1. The system should be powered on and ready to use.
2. The user should be service user.
3. A plan should be ready to load and run.
4. The system should be in service mode.
<<<
STEPS: >>>
1. Start the system with power on.
2. Click Service symbol in the left panel.
3. Check system pressure values.
4. Load a treatment plan.
5. Start the treatment.
6. Click Service symbol in the left panel.
7. Check system pressure values.
<<<
EXPECTED_BEHAVIOR: >>>
1. Verify the system is on and no treatment plan is loaded.
2. Verify the services displayed in the GUI.
3. Verify it’s below 1 psi.
4. Verify the plan is loaded successfully.
5. Verify the treatment started.
6. Verify the services displayed in the GUI.
7. Verify it’s above 1 psi.
<<<
RELATIONS:
- TYPE: Parent
  VALUE: RQ-H1FHI-13
  ROLE: Verifies

[TEST_CASE]
UID: TC-H1FHI-17
TITLE: Illumination LEDs - Test Case
STATEMENT: >>>
Verify that successive press-and-release cycles of the illumination membrane button advance the
illumination LEDs through Dim Brightness, Normal Brightness, High Brightness, Breathing Effect,
Off, and then back to Dim Brightness.
<<<
PREREQUISITES: >>>
1. System is ready to run.
2. No treatment plan is running.
3. The illumination LEDs are Off.
4. PWM duty cycle at the illumination LED output and elapsed time can be measured.
<<<
STEPS: >>>
1. Press and release the illumination membrane button.
2. Verify the illumination LEDs are in Dim Brightness mode at 10% PWM duty cycle.
3. Press and release the illumination membrane button.
4. Verify the illumination LEDs are in Normal Brightness mode at 20% PWM duty cycle.
5. Press and release the illumination membrane button.
6. Verify the illumination LEDs are in High Brightness mode at 30% PWM duty cycle.
7. Press and release the illumination membrane button.
8. Verify the illumination LEDs are in Breathing Effect mode, smoothly cycling from 0% to 30% and
   back to 0% over a 3-second period.
9. Press and release the illumination membrane button.
10. Verify the illumination LEDs are Off at 0% PWM duty cycle.
11. Press and release the illumination membrane button.
12. Verify the illumination LEDs are back in Dim Brightness mode at 10% PWM duty cycle.
<<<
EXPECTED_BEHAVIOR: >>>
1. Each press-and-release cycle advances the illumination LEDs by exactly one mode in the specified
   sequence, including the transition from Off back to Dim Brightness.
2. The measured PWM levels and breathing period match the specified values for every mode.
<<<
RELATIONS:
- TYPE: Parent
  VALUE: RQ-H1FHI-6
  ROLE: Verifies

[TEST_CASE]
UID: TC-H1FHI-18
TITLE: Indicator LEDs 2 - Test Case
STATEMENT: >>>
Verify every supported indicator LED sequence, including its color, spatial pattern, timing, and
transition from the previously active effect.
<<<
PREREQUISITES: >>>
1. The head interface and indicator LED ring are powered.
2. A UART control tool is connected at the configured head-interface baud rate and can send valid
   normal-firmware 12-byte command packets with duplicated values and complements.
3. The tester can observe the complete 51-LED ring and measure elapsed time.
<<<
STEPS: >>>
1. Send ``LED_SEQ_OFF`` (0) and observe the ring.
2. Send ``LED_SEQ_COLD`` (1) and observe one complete pulse cycle.
3. Send ``LED_SEQ_WARMUP`` (2) and observe one complete pulse cycle and one complete rotation.
4. Send ``LED_SEQ_PRIMED`` (4) and observe at least two color transitions.
5. Send ``LED_SEQ_SETUP`` (5) and observe one complete rotation.
6. Send ``LED_SEQ_READY`` (6) and observe the ring.
7. Send ``LED_SEQ_XRAY`` (7) and observe one complete pulse cycle.
8. Send ``LED_SEQ_IDLE`` (8) and observe the ring.
9. Send ``LED_SEQ_FAULT`` (9) and observe at least two on/off transitions.
10. Send sequence ID 3 and observe the ring.
<<<
EXPECTED_BEHAVIOR: >>>
1. Sequence 0 turns every LED off.
2. Sequence 1 smoothly pulses white over a 3-second cycle.
3. Sequence 2 displays a 15-LED purple segment that advances every 75 msec while smoothly pulsing
   over a 3-second cycle.
4. Sequence 4 alternates the full ring between blue and green every 500 msec.
5. Sequence 5 displays separate six-LED blue and orange segments on a dark ring. Blue leads orange
   by 14 LED positions, and both advance every 75 msec.
6. Sequence 6 displays solid green.
7. Sequence 7 smoothly pulses amber over a 3-second cycle.
8. Sequence 8 displays solid white.
9. Sequence 9 flashes red on and off every 250 msec.
10. Sequence ID 3 is unsupported and causes the ring to turn off.
<<<
RELATIONS:
- TYPE: Parent
  VALUE: RQ-H1FHI-14
  ROLE: Verifies

[TEST_CASE]
UID: TC-H1FHI-19
TITLE: Cooling System Temperature - Test Case
STATEMENT: >>>
When a service user power on the system without loading any treatment plan, he/she be able to see the water temperature on GUI.
<<<
PREREQUISITES: >>>
1. The system is stable and ready to run
2. User has to be a service user.
3. The system should be in service mode
<<<
STEPS: >>>
1. Service user should Power on the system
2. Click the Service symbol in the left panel of the screen
<<<
EXPECTED_BEHAVIOR: >>>
1. Verify the system is powered on and is in a stable mode and ready to run. Also, verify there isn’t any treatment plan loaded in the system
2. Verify the temperature of the water which should be between 10C and 40C.
<<<
RELATIONS:
- TYPE: Parent
  VALUE: RQ-H1FHI-1
  ROLE: Verifies

[TEST_CASE]
UID: TC-H1FHI-21
TITLE: Main Board Communication - Test Case
STATEMENT: >>>
Verify that the head interface receives a complete control packet transmitted contiguously at the
configured UART baud rate and reports values to the main control board at a rate greater than 1 Hz.
<<<
PREREQUISITES: >>>
1. The system is powered on and ready to run.
2. A UART control and monitoring tool is connected to the head interface's main-control UART.
3. The tool can send a valid 12-byte normal-firmware control packet and timestamp reported data
   packets. For calibration firmware, it can send the legacy 8-byte indicator control packet.
<<<
STEPS: >>>
1. Configure the control and monitoring tool for the head interface UART baud rate.
2. Send a valid 12-byte normal-firmware control packet as one contiguous transmission, without
   delays between bytes. Request a known indicator LED state in bytes 0 through 7 and Stopped QC
   state in bytes 8 through 11 using duplicated values and complements.
3. Observe the indicator LED ring.
4. Monitor and timestamp the data packets reported by the head interface for at least 2 seconds.
<<<
EXPECTED_BEHAVIOR: >>>
1. The UART tool communicates with the head interface.
2. The head interface accepts the complete control packet and the indicator LED ring displays the
   requested state.
3. The head interface reports data packets periodically at a rate greater than 1 Hz.
<<<
RELATIONS:
- TYPE: Parent
  VALUE: RQ-H1FHI-8
  ROLE: Verifies

[TEST_CASE]
UID: TC-H1FHI-22
TITLE: Collimator - Test Case
STATEMENT: >>>
The service user should be able to check the reported ID of the attached collimator and, if it’s disconnected, the reported ID should be 0.
<<<
PREREQUISITES: >>>
1. The user should be service user
2. The system should be powered on without any collimator connected to it.
3. The system should be in service mode
<<<
STEPS: >>>
1. the collimator should be disconnected by service user
2. power on the system
3. Check the head interface board
4. Connect the collimator
5. Check the head interface board
<<<
EXPECTED_BEHAVIOR: >>>
1. Verify the collimator is disconnected
2. Verify system is ready to use and there is no treatment plan loaded to the system.
3. Verify the reported ID is 0 for the collimator
4. Verify the collimator is connected
5. Verify the reported ID is updated accordingly with the connected collimator
<<<
RELATIONS:
- TYPE: Parent
  VALUE: RQ-H1FHI-9
  ROLE: Verifies

[TEST_CASE]
UID: TC-H1FHI-23
TITLE: Magnetometers readings - Test Case
STATEMENT: >>>
The service user can view each magnetometer feedback reporting data in the service screen, which has to be non-zero values.
<<<
PREREQUISITES: >>>
1. The user should be service user
2. The system should be powered on without any collimator connected to it.

3. The system should be in service mode
4. There is no treatment plan loaded into the system
<<<
STEPS: >>>
1. Power on the system
2. Click services symbol in the lefthand side panel
3. Check the service screen
<<<
EXPECTED_BEHAVIOR: >>>
1. Verify the system powered on successfully without any treatment plan loaded on it.
2. Verify the service screen is displayed in the GUI
3. Verify each magnetometer feedback displayed on screen is non-zero.
<<<
RELATIONS:
- TYPE: Parent
  VALUE: RQ-H1FHI-10
  ROLE: Verifies

[TEST_CASE]
UID: TC-H1FHI-24
TITLE: Membrane key switches - Test Case
STATEMENT: >>>
Verify that a service user can view the state of each of the 5 membrane key switches and that input
transitions are subject to the 30 msec debounce interval.
<<<
PREREQUISITES: >>>
1. The user should be service user
2. The system should be powered on without any treatment plan loaded.
3. The system should be in service mode
4. The membrane key inputs can be driven with controlled transition timing.
<<<
STEPS: >>>
1. Check the system when it is powered on
2. Click the Service symbol in the left panel of the screen
3. Check the services screen
4. For each of the 5 membrane key inputs, apply a state pulse shorter than 30 msec and observe its
   value on the service screen.
5. Hold each input in its changed state for longer than 30 msec and observe its value on the service
   screen.
6. Return each input to its original state for longer than 30 msec and observe its value on the
   service screen.
<<<
EXPECTED_BEHAVIOR: >>>
1. Verify the system is ready to use with no treatment plan loaded.
2. Verify the service screen is displayed.
3. Verify each pulse shorter than 30 msec is ignored and does not change the reported state.
4. Verify each state transition held longer than 30 msec is accepted and accurately reported for
   all 5 membrane key inputs.
<<<
RELATIONS:
- TYPE: Parent
  VALUE: RQ-H1FHI-11
  ROLE: Verifies

[TEST_CASE]
UID: TC-H1FHI-25
TITLE: Cooling system flow - Test Case
STATEMENT: >>>
The service user should be able to view system flow values in the
services screen.
<<<
PREREQUISITES: >>>
1. The user should be service user
2. The system should be powered on without any treatment plan loaded.
3. The system should be in service mode
4. There should be a treatment plan ready to load into the system.
<<<
STEPS: >>>
1. The head interface firmware shall be able to read and convert a PWM feedback signal for monitoring the cooling system’s flow sensor readings
<<<
EXPECTED_BEHAVIOR: >>>
1. Verify the firmware can read and convert a PWM feedback signal for monitoring the cooling system’s flow sensor readings
<<<
RELATIONS:
- TYPE: Parent
  VALUE: RQ-H1FHI-12
  ROLE: Verifies

[TEST_CASE]
UID: TC-H1FHI-54
TITLE: QC Read - Test Case
STATEMENT: >>>
Verify the head interface can read and report x-ray sensor data from the QC collimator's analog diode.
<<<
PREREQUISITES: >>>
1. The user should be a service user.
2. The system should be powered on and in service mode.
3. The QC collimator should be mounted and connected.
<<<
STEPS: >>>
1. Power on the system
2. Load a treatment plan with an input of 50 kV / 20 sec.
3. Run the treatment plan
4. Monitor QC Channel 0 Reading on Monitored Parameters in the Service Tab
5. Repeat step 2 to 4 with an input of 70 kV / 20 sec.
<<<
EXPECTED_BEHAVIOR: >>>
1. Verify QC Channel 0 Reading is between 400 counts and 700 counts for an input of 50 kV
2. Verify QC Channel 0 Reading is between 1800 counts and 2200 counts for an input of 70 kV
<<<
RELATIONS:
- TYPE: Parent
  VALUE: RQ-H1FHI-53
  ROLE: Verifies

[TEST_CASE]
UID: TC-H1FHI-56
TITLE: Robot Hand Guidance Button Test - Test Case
STATEMENT: >>>
Service user should verify that the robot arm moves in manually guided positions when the button is pressed down and holds its position
upon release.
<<<
PREREQUISITES: >>>
1. The user should be service user
2. The system should be powered on
3. The robot arm should be ready and in a safe, reachable position to move
<<<
STEPS: >>>
1. Check the system is powered on
2. Check the robot status LED and robot controller to ensure arm is ready for hand guidance
3. If the button is not safely reachable, use the GUI to change the arm to the “Treatment” position
4. With one hand holding the opposite side of the treatment hand, and the other holding the bar with the manual guidance button, press and hold the button down
5. Gently push the robot arm in all 6 directions: forward, backward, left, right, up, and down, within comfortable reach
6. Release the robot hand guidance button
<<<
EXPECTED_BEHAVIOR: >>>
1. The system should appear in normal operation with no interlocks or errors tripped.
2. The system should be on, and the robot arm LED should be flashing blue
3. The robot arm moves to the treatment position with no issues. The head can be reached.
4. The robot arm should have a relay that has an audible click once the button is engaged. The LEDs on the robot arm should change color. The robot arm should respond to the button press in under 1 second.
5. The robot arm should move in all directions smoothly without interruption.
6. The robot arm relay should have an audible click again. The LED’s on the robot arm return to the ready state color. The robot arm holds its position within 1 second of the button’s release. The robot arm is immovable with the same pressure applied in Step 5.
<<<
RELATIONS:
- TYPE: Parent
  VALUE: RQ-H1FHI-55
  ROLE: Verifies

[[/SECTION]]
